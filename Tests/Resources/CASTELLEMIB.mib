-- CASTELLE-COMMON-MIB
-- file: castelle.mib version 1.0  03/08/98
-- Common MIB Release 2.0


CASTELLEMIB DEFINITIONS ::= BEGIN

-- SECTION 1: Top Level Definitions

-- Imports

IMPORTS
    enterprises, Gauge,
		NetworkAddress, Counter, Gauge,
    TimeTicks, IpAddress      FROM RFC1155-SMI
    PhysAddress, DisplayString   FROM RFC1213-MIB
    OBJECT-TYPE           FROM RFC-1212 -- RFC1212
		TRAP-TYPE						FROM RFC-1215; -- RFC1215;

-- Textual Conventions
-- Categories

castelle            OBJECT IDENTIFIER ::=  { enterprises 726 }

products            OBJECT IDENTIFIER ::=  { castelle 1 }
temporary            OBJECT IDENTIFIER ::=  { castelle 2 }
registration          OBJECT IDENTIFIER ::=  { castelle 3 }


--Groups

printerServer          OBJECT IDENTIFIER ::=  {products 1 }
faxServer            OBJECT IDENTIFIER ::=  {products 2 }
commServer           OBJECT IDENTIFIER ::=  {products 3 }
others             OBJECT IDENTIFIER ::=  {products 4 }


--Products Registration
--These objects identifiers are used as values for sysObjectsId.

pServerReg          OBJECT IDENTIFIER ::=  {registration 1}
fServerReg          OBJECT IDENTIFIER ::=  {registration 2}
cServerReg          OBJECT IDENTIFIER ::=  {registration 3}


faxpress1000     OBJECT IDENTIFIER ::= {fServerReg 1}
faxpress1500     OBJECT IDENTIFIER ::= {fServerReg 2}
faxpress2000     OBJECT IDENTIFIER ::= {fServerReg 3}
faxpress3000     OBJECT IDENTIFIER ::= {fServerReg 4}
faxpress3500     OBJECT IDENTIFIER ::= {fServerReg 5}
faxpress4000     OBJECT IDENTIFIER ::= {fServerReg 6}
faxpress4500     OBJECT IDENTIFIER ::= {fServerReg 7}


-- Product infomation group

fPProduct      OBJECT IDENTIFIER ::=  {faxServer 1 }

fPModel OBJECT-TYPE
   SYNTAX DisplayString (SIZE(0..48))
   ACCESS read-only
   STATUS mandatory
   DESCRIPTION
      "The FaxPress Model."
   ::= {fPProduct 1}

fPNetType OBJECT-TYPE
--  SYNTAX INTEGER {ethernet(1), tokenring(2)}
   SYNTAX DisplayString (SIZE(0..48))
   ACCESS read-only
   STATUS mandatory
   DESCRIPTION
      "The FaxPress network interface type. ETHERNET/TOKENRING"
   ::= {fPProduct 2}

fPSerialNum OBJECT-TYPE
   SYNTAX DisplayString (SIZE(0..9))
   ACCESS read-only
   STATUS mandatory
   DESCRIPTION
      "The product serial number"
   ::= {fPProduct 3}

fPRevision OBJECT-TYPE
   SYNTAX DisplayString (SIZE(0..10))
   ACCESS read-only
   STATUS mandatory
   DESCRIPTION
      "The FaxPress software revision number."
   ::= {fPProduct 4}

fPBuildDate OBJECT-TYPE
   SYNTAX DisplayString (SIZE(0..30))
   ACCESS read-only
   STATUS mandatory
   DESCRIPTION
      "The FaxpPress software building date"
   ::= {fPProduct 5}

fPSystemName OBJECT-TYPE
   SYNTAX DisplayString (SIZE(0..30))
   ACCESS read-write
   STATUS mandatory
   DESCRIPTION
      "The FaxpPress name assigned by user"
   ::= {fPProduct 6}

fPLocation OBJECT-TYPE
   SYNTAX DisplayString (SIZE(0..80))
   ACCESS read-write
   STATUS optional
   DESCRIPTION
      "The FaxpPress location"
   ::= {fPProduct 7}

fPStatus OBJECT-TYPE
   SYNTAX DisplayString (SIZE(0..80))
   ACCESS read-only
   STATUS optional
   DESCRIPTION
      "The FaxpPress status:"
   ::= {fPProduct 8}

fPContact OBJECT-TYPE
   SYNTAX DisplayString (SIZE(0..48))
   ACCESS read-write
   STATUS optional
   DESCRIPTION
      "The FaxpPress Contact User Name:"
   ::= {fPProduct 9}

fPUpTime OBJECT-TYPE
   SYNTAX TimeTicks
   ACCESS read-only
   STATUS optional
   DESCRIPTION
      "The time since the FaxpPress has been running:"
   ::= {fPProduct 10}


--Hardware infomation group

fPHWInfo      OBJECT IDENTIFIER ::=  {faxServer 2 }

fPPcb OBJECT-TYPE
   SYNTAX DisplayString (SIZE(0..48))
   ACCESS read-only
   STATUS mandatory
   DESCRIPTION
      "Main board Type"
   ::= {fPHWInfo 1}

fPTotalFaxLines OBJECT-TYPE
   SYNTAX INTEGER (1..16)
   ACCESS read-only
   STATUS mandatory
   DESCRIPTION
      "The number of total fax lines"
   ::= {fPHWInfo 2}

--fPTotalParaPorts OBJECT-TYPE
--   SYNTAX INTEGER (0..1)
--   ACCESS read-only
--   STATUS mandatory
--   DESCRIPTION
--      "The number of total parallel ports"
--   ::= {fPHWInfo 3}
--
--fPTotalSerialPorts OBJECT-TYPE
--   SYNTAX INTEGER (0..1)
--   ACCESS read-only
--   STATUS mandatory
--   DESCRIPTION
--      "The number of total Serial ports"
--   ::= {fPHWInfo 4}

fPMemorySize OBJECT-TYPE
   SYNTAX INTEGER
   ACCESS read-only
   STATUS mandatory
   DESCRIPTION
      "The size of memory on board "
   ::= {fPHWInfo 5}

fPFreeMem OBJECT-TYPE
   SYNTAX INTEGER
   ACCESS read-only
   STATUS mandatory
   DESCRIPTION
      "The size of current free memory"
   ::= {fPHWInfo 6}

fPFsDiskSpace OBJECT-TYPE
   SYNTAX INTEGER
   ACCESS read-only
   STATUS mandatory
   DESCRIPTION
      "The size of current File Server's free disk space"
   ::= {fPHWInfo 7}


--FaxPress Configuration group
fPConfigInfo      OBJECT IDENTIFIER ::=  {faxServer 3}

fPNOSSetting OBJECT-TYPE
   SYNTAX INTEGER {NetWare(1), WintNT(2)}
   ACCESS read-only
   STATUS mandatory
   DESCRIPTION
      "FaxPress Network OS setting: 1--Netware 2--NT After setting need to reboot the FaxPress to take into effect"
   ::= {fPConfigInfo 1}

fPWinNTConfig     	OBJECT IDENTIFIER ::=  {fPConfigInfo 2}

fPWinNTServerName OBJECT-TYPE
   SYNTAX DisplayString (SIZE(0..48))
   ACCESS read-only
   STATUS optional
   DESCRIPTION
      "WinNT server name which Faxpress was inistalled"
   ::= {fPWinNTConfig 1}

fPWinNTShareDir OBJECT-TYPE
   SYNTAX DisplayString (SIZE(0..128))
   ACCESS read-only
   STATUS optional
   DESCRIPTION
      "Shareable directory name which faxpress was installed"
   ::= {fPWinNTConfig 2}

fPWinNTAddr OBJECT-TYPE
   SYNTAX IpAddress
   ACCESS read-only
   STATUS optional
   DESCRIPTION
       "WinNT server Internet Address"
   ::= {fPWinNTConfig 3}

fPWinNTPasswd OBJECT-TYPE
   SYNTAX DisplayString (SIZE(0..48))
   ACCESS read-only
   STATUS optional
   DESCRIPTION
       "WinNT server login password"
   ::= {fPWinNTConfig 4}


fPNetWareConfig     OBJECT IDENTIFIER ::=  {fPConfigInfo 3}

fPNetWareMode OBJECT-TYPE
   SYNTAX INTEGER {Bindery(0), NDS(1)}
   ACCESS read-only
   STATUS optional
   DESCRIPTION
       "Novell NetWare OS type"
   ::= {fPNetWareConfig 1}

fPBinderyConfig     OBJECT IDENTIFIER ::=  {fPNetWareConfig 2}

fPBinderyFSName OBJECT-TYPE
   SYNTAX DisplayString (SIZE(0..48))
   ACCESS read-only
   STATUS optional
   DESCRIPTION
      "NetWare 3.x master server name which Faxpress was inistalled"
   ::= {fPBinderyConfig 1}

fPBinderyVolume OBJECT-TYPE
   SYNTAX DisplayString (SIZE(0..8))
   ACCESS read-only
   STATUS optional
   DESCRIPTION
      "NetWare 3.x volume name which Faxpress was inistalled"
   ::= {fPBinderyConfig 2}

fPBinderyRootDir OBJECT-TYPE
   SYNTAX DisplayString (SIZE(0..48))
   ACCESS read-only
   STATUS optional
   DESCRIPTION
      "Root directory name which Faxpress was inistalled"
   ::= {fPBinderyConfig 3}


fPBinderyPasswd OBJECT-TYPE
   SYNTAX DisplayString (SIZE(0..48))
   ACCESS read-only
   STATUS optional
   DESCRIPTION
      "NetWare file server login password"
   ::= {fPBinderyConfig 4}


fPNDSConfig       OBJECT IDENTIFIER ::=  {fPNetWareConfig 3}

fPNDSTreeName OBJECT-TYPE
   SYNTAX DisplayString (SIZE(0..48))
   ACCESS read-only
   STATUS optional
   DESCRIPTION
      "Novell NetWare 4.x NDS tree name"
   ::= {fPNDSConfig 1}

fPNDSContext OBJECT-TYPE
   SYNTAX DisplayString (SIZE(0..48))
   ACCESS read-only
   STATUS optional
   DESCRIPTION
      "NDS Context used by Faxpress"
   ::= {fPNDSConfig 2}


fPNDSFSName OBJECT-TYPE
   SYNTAX DisplayString (SIZE(0..48))
   ACCESS read-only
   STATUS optional
   DESCRIPTION
      "NetWare 4.x file server name which Faxpress was inistalled"
   ::= {fPNDSConfig 3}

fPNDSFSVolume OBJECT-TYPE
   SYNTAX DisplayString (SIZE(0..48))
   ACCESS read-only
   STATUS optional
   DESCRIPTION
      "the volume name which Faxpress was inistalled"
   ::= {fPNDSConfig 4}

fPNDSFSRootDir OBJECT-TYPE
   SYNTAX DisplayString (SIZE(0..48))
   ACCESS read-only
   STATUS optional
   DESCRIPTION
      "the root directory which Faxpress was inistalled"
   ::= {fPNDSConfig 5}


fPNDSFSPasswd OBJECT-TYPE
   SYNTAX DisplayString (SIZE(0..48))
   ACCESS read-only
   STATUS optional
   DESCRIPTION
      "Faxpress password"
   ::= {fPNDSConfig 6}


fPTcpConfig     	OBJECT IDENTIFIER ::=  {fPConfigInfo 4}

fPTcpAddr OBJECT-TYPE
   SYNTAX IpAddress
   ACCESS read-write
   STATUS mandatory
   DESCRIPTION
       "Faxpress Internet Address"
   ::= {fPTcpConfig 1}

fPNetMask OBJECT-TYPE
   SYNTAX IpAddress
   ACCESS read-write
   STATUS mandatory
   DESCRIPTION
       "Faxpress subnet mask"
   ::= {fPTcpConfig 2}

fPGateway OBJECT-TYPE
   SYNTAX IpAddress
   ACCESS read-write
   STATUS mandatory
   DESCRIPTION
       "Faxpress default gateway address"
   ::= {fPTcpConfig 3}

fPMultiProtocol OBJECT-TYPE
   SYNTAX INTEGER {No(0), Yes(1)}
   ACCESS read-only
   STATUS mandatory
   DESCRIPTION
       "Multi Protocol Support"
   ::= {fPConfigInfo 5}


fPKeepOutgoingJobsInfo    OBJECT IDENTIFIER ::=  {fPConfigInfo 6}

fPKeepOutgoingJobs OBJECT-TYPE
   SYNTAX DisplayString (SIZE(0..16))
   ACCESS read-write
   STATUS mandatory
   DESCRIPTION
      "the setting to keep outgoing fax after sending: Yes/No"
   ::= {fPKeepOutgoingJobsInfo 1}


fPStorageInfo      OBJECT IDENTIFIER ::=  {fPConfigInfo 7}

fPStorageReclamation OBJECT-TYPE
   SYNTAX INTEGER {Disable(2), Enable(1)}
   ACCESS read-write
   STATUS mandatory
   DESCRIPTION
      "Automatic storage reclamation setting: 1-Enable 2-Disable"
   ::= {fPStorageInfo 1}

fPFaxAge OBJECT-TYPE
   SYNTAX INTEGER
   ACCESS read-write
   STATUS mandatory
   DESCRIPTION
      "the number of days that older incoming fax and Notice will be deleted"
   ::= {fPStorageInfo 2}

fPLogAge OBJECT-TYPE
   SYNTAX INTEGER
   ACCESS read-write
   STATUS mandatory
   DESCRIPTION
      "the number of months that old log files will be deleted"
   ::= {fPStorageInfo 3}

fPPurgeTime OBJECT-TYPE
   SYNTAX DisplayString (SIZE(0..8))
   ACCESS read-write
   STATUS mandatory
   DESCRIPTION
      "the time to clean up"
   ::= {fPStorageInfo 4}


--fPBillCodeInfo     OBJECT IDENTIFIER ::=  {fPConfigInfo 8}

--fPBillCodeTable OBJECT-TYPE
--   SYNTAX SEQUENCE OF FPBillCodeEntry
--   ACCESS not-accessible
--   STATUS mandatory
--   DESCRIPTION
--      "Bill back code list"
--   ::= {fPBillCodeInfo 1}


--fPBillCodeEntry OBJECT-TYPE
--   SYNTAX FPBillCodeEntry
--   ACCESS not-accessible
--   STATUS mandatory
--   DESCRIPTION
--      "bill back code entry"
--   INDEX {fPBillCode}
--   ::= {fPBillCodeTable 1}


--FPBillCodeEntry ::=
--   SEQUENCE {
--   fPBillCode
--     DisplayString
--	 }


--fPBillCode OBJECT-TYPE
--   SYNTAX DisplayString (SIZE(0..48))
--   ACCESS read-write
--   STATUS mandatory
--   DESCRIPTION
--      "Bill back code."
--   ::= {fPBillCodeEntry 1}


--Fax port infomation group
fPFaxLineInfo      OBJECT IDENTIFIER ::=  {faxServer 4}

fPFaxLineTable OBJECT-TYPE
   SYNTAX SEQUENCE OF FPFaxLineEntry
   ACCESS not-accessible
   STATUS mandatory
   DESCRIPTION
      "A list about fax line configurtion."
   ::= {fPFaxLineInfo 1}


fPFaxLineEntry OBJECT-TYPE
   SYNTAX FPFaxLineEntry
   ACCESS not-accessible
   STATUS mandatory
   DESCRIPTION
      "Configuration value for one fax line"
   INDEX {faxLineIndex}
   ::= {fPFaxLineTable 1}


FPFaxLineEntry ::=
   SEQUENCE {
   faxLineIndex
     INTEGER,
   femoteTermID
     DisplayString,
   imprintTermID
     DisplayString,
 	 localNumber
     DisplayString,
	 pbxPreDial
     DisplayString,
	 dialMode
     DisplayString,
	 lineDirection
     DisplayString,
	 routingType
     DisplayString,
	 routeToUser
     DisplayString
   }


faxLineIndex OBJECT-TYPE
   SYNTAX INTEGER
   ACCESS read-only
   STATUS mandatory
   DESCRIPTION
      "A unique vale for each phone line."
   ::= {fPFaxLineEntry 1}


remoteTermID OBJECT-TYPE
   SYNTAX DisplayString (SIZE(0..48))
   ACCESS read-write
   STATUS mandatory
   DESCRIPTION
      "Remote terminal ID shown on LED"
   ::= {fPFaxLineEntry 2}


imprintTermID OBJECT-TYPE
   SYNTAX DisplayString (SIZE(0..48))
   ACCESS read-write
   STATUS mandatory
   DESCRIPTION
      "Imprint terminal ID shown on the head line of fax"
   ::= {fPFaxLineEntry 3}

localNumber OBJECT-TYPE
   SYNTAX DisplayString (SIZE(0..48))
   ACCESS read-write
   STATUS mandatory
   DESCRIPTION
      "the local phone number into this fax phone line"
   ::= {fPFaxLineEntry 4}

pbxPreDial OBJECT-TYPE
   SYNTAX DisplayString (SIZE(0..2))
   ACCESS read-write
   STATUS mandatory
   DESCRIPTION
      "PBX Pre-Dial number: one digit"
   ::= {fPFaxLineEntry 5}

dialMode OBJECT-TYPE
   SYNTAX DisplayString (SIZE(0..8))
   ACCESS read-write
   STATUS mandatory
   DESCRIPTION
      "Dial mode: Tone/Pulse"
   ::= {fPFaxLineEntry 6}

lineDirection OBJECT-TYPE
--  SYNTAX INTEGER {BiDirection(1), Input(2), Output(3), NotConnect(0)}
   SYNTAX DisplayString (SIZE(0..16))
   ACCESS read-write
   STATUS mandatory
   DESCRIPTION
      "Line direction setting: Input/Output/BiDirection/NotConnected"
   ::= {fPFaxLineEntry 7}

routingType OBJECT-TYPE
   SYNTAX DisplayString (SIZE(0..8))
   ACCESS read-write
   STATUS mandatory
   DESCRIPTION
      "Inbound fax routing type: DTMF/DID/None"
   ::= {fPFaxLineEntry 8}


routeToUser OBJECT-TYPE
   SYNTAX DisplayString (SIZE(0..48))
   ACCESS read-write
   STATUS mandatory
   DESCRIPTION
      "Inbound fax routing to the user name"
   ::= {fPFaxLineEntry 9}


-- FaxPress status group
fPQmrStatus     OBJECT IDENTIFIER ::=  {faxServer 5}

fPInputJobs OBJECT-TYPE
--   SYNTAX Counter
   SYNTAX INTEGER
   ACCESS read-write
   STATUS mandatory
   DESCRIPTION
      "The number of incoming faxes received"
   ::= {fPQmrStatus 1}

fPInputJobsInQueue OBJECT-TYPE
   SYNTAX Gauge
   ACCESS read-only
   STATUS mandatory
   DESCRIPTION
      "The number of incoming faxes in unaddressed queue"
   ::= {fPQmrStatus 2}


fPOutputJobs OBJECT-TYPE
--   SYNTAX Counter
   SYNTAX INTEGER
   ACCESS read-write
   STATUS mandatory
   DESCRIPTION
      "The number of faxes sent"
   ::= {fPQmrStatus 3}


fPOutputJobsInQueue OBJECT-TYPE
   SYNTAX Gauge
   ACCESS read-only
   STATUS mandatory
   DESCRIPTION
      "The number of outgoing faxes in output queue to be sent"
   ::= {fPQmrStatus 4}


fPFailedJobs OBJECT-TYPE
--   SYNTAX Counter
   SYNTAX INTEGER
   ACCESS read-write
   STATUS mandatory
   DESCRIPTION
      "The number of failed outgoing faxes"
   ::= {fPQmrStatus 5}

fPCurrentUsers OBJECT-TYPE
   SYNTAX Gauge
   ACCESS read-only
   STATUS mandatory
   DESCRIPTION
      "The number of current login users"
   ::= {fPQmrStatus 6}

--fPFailedTrigger OBJECT-TYPE
--   SYNTAX INTEGER {Disable(0), Enable(1)}
--   ACCESS read-write
--   STATUS mandatory
--   DESCRIPTION
--      "Trap enable setting for failed faxes"
--   ::= {fPQmrStatus 7}

--fPFailedTriggerLimit OBJECT-TYPE
--   SYNTAX INTEGER(0..100)
--   ACCESS read-write
--   STATUS mandatory
--   DESCRIPTION
--      "The percentage of faild jobs which triggers trap"
--   ::= {fPQmrStatus 8}


--fPOutputTrigger OBJECT-TYPE
--   SYNTAX INTEGER {Disable(0), Enable(1)}
--   ACCESS read-write
--   STATUS mandatory
--   DESCRIPTION
--      "Trap enable setting for un-processed faxes in queue"
--   ::= {fPQmrStatus 9}

--fPOutputLimit OBJECT-TYPE
--   SYNTAX INTEGER
--   ACCESS read-write
--   STATUS mandatory
--   DESCRIPTION
--      "The upper limit of jobs in outgoing queue which triggers trap "
--   ::= {fPQmrStatus 10}


-- FaxPress fax line status group
fPLineStatus     OBJECT IDENTIFIER ::=  {faxServer 6}

fPLineStatusTable OBJECT-TYPE
   SYNTAX SEQUENCE OF FPLineStatusEntry
   ACCESS not-accessible
   STATUS mandatory
   DESCRIPTION
     "The fax line status entry"
   ::= {fPLineStatus 1}


fPLineStatusEntry OBJECT-TYPE
   SYNTAX FPLineStatusEntry
   ACCESS not-accessible
   STATUS mandatory
   DESCRIPTION
      "one entry in line status table"
   INDEX {fPLineIndex}
   ::= {fPLineStatusTable 1}


FPLineStatusEntry ::=
   SEQUENCE {
   fPLineIndex
     INTEGER,
   fPLineCurrentStatus
     DisplayString,
   fPLineInputCalls
--     Counter,
     INTEGER,
   fPLineOutputCalls
--     Counter,
     INTEGER,
   fPLineFailedRcvCalls
--     Counter,
     INTEGER,
   fPLineFailedXmtCalls
--     Counter,
     INTEGER,
   fPLineRecentFailPercentage
     INTEGER,
   fPLineTrigger
     INTEGER
--    Counter,
--  fPLineTrigger
--    INTEGER
--  fPLineTriggerLimit
--    INTEGER
	}


fPLineIndex OBJECT-TYPE
   SYNTAX INTEGER
   ACCESS read-only
   STATUS mandatory
   DESCRIPTION
     "The fax line index"
   ::= {fPLineStatusEntry 1}


fPLineCurrentStatus OBJECT-TYPE
   SYNTAX DisplayString (SIZE(0..16))
   ACCESS read-only
   STATUS mandatory
   DESCRIPTION
     "the current fax line status: Idle/Receiving/Sending"
   ::= {fPLineStatusEntry 2}


fPLineInputCalls OBJECT-TYPE
--   SYNTAX Counter
   SYNTAX INTEGER
   ACCESS read-write
   STATUS mandatory
   DESCRIPTION
     "the number of receiving calls"
   ::= {fPLineStatusEntry 3}


fPLineOutputCalls OBJECT-TYPE
--   SYNTAX Counter
   SYNTAX INTEGER
   ACCESS read-write
   STATUS mandatory
   DESCRIPTION
     "the number of sending calls"
   ::= {fPLineStatusEntry 4}


fPLineFailedRcvCalls OBJECT-TYPE
--   SYNTAX Counter
   SYNTAX INTEGER
   ACCESS read-write
   STATUS mandatory
   DESCRIPTION
     "the number of failed receiving calls"
   ::= {fPLineStatusEntry 5}

fPLineFailedXmtCalls OBJECT-TYPE
--   SYNTAX Counter
   SYNTAX INTEGER
   ACCESS read-write
   STATUS mandatory
   DESCRIPTION
     "the number of failed sending calls"
   ::= {fPLineStatusEntry 6}

fPLineRecentFailPercentage OBJECT-TYPE
   SYNTAX INTEGER
   ACCESS read-only
   STATUS mandatory
   DESCRIPTION
     "the percentage of failed calls during recent 16 calls"
   ::= {fPLineStatusEntry 7}

fPLineTrigger OBJECT-TYPE
   SYNTAX INTEGER
   ACCESS read-write
   STATUS mandatory
   DESCRIPTION
     "TRAP Trigger enable setting as the percentage value of faied calls during recent 16 calls. 0--diabled 10-100 as the percentage value."
   ::= {fPLineStatusEntry 8}

--fPLineTrigger OBJECT-TYPE
--   SYNTAX INTEGER {Disable(0), Enable(1)}
--   ACCESS read-write
--   STATUS mandatory
--   DESCRIPTION
--     "TRAP Trigger enable setting"
--   ::= {fPLineStatusEntry 7}

--fPLineTriggerLimit OBJECT-TYPE
--   SYNTAX INTEGER(0..100)
--   ACCESS read-write
--   STATUS mandatory
--   DESCRIPTION
--     "the percentage of failed jobs which triggers TRAP"
--   ::= {fPLineStatusEntry 8}


-- FaxPress printer status group
fPPrinterStatus    OBJECT IDENTIFIER ::=  {faxServer 7}

fPPara    OBJECT IDENTIFIER ::=  {fPPrinterStatus 1}

fPParaStatus OBJECT-TYPE
   SYNTAX DisplayString (SIZE(0..16))
   ACCESS read-only
   STATUS mandatory
   DESCRIPTION
     "the current parallel port status: Idle/Printing/Offline/Paperout "
   ::= {fPPara 1}

fPParaJobs OBJECT-TYPE
--   SYNTAX Counter
   SYNTAX INTEGER
   ACCESS read-write
   STATUS mandatory
   DESCRIPTION
     "the nuber of printed jobs on this parallel port "
   ::= {fPPara 2}

fPParaTrigger OBJECT-TYPE
--  SYNTAX INTEGER{Disable(0), Enable(1)}
   SYNTAX DisplayString (SIZE(0..16))
   ACCESS read-write
   STATUS optional
   DESCRIPTION
     " this setting trap when printer is not ready for printing: Enable/Disable"
   ::= {fPPara 3}


fPSerial  OBJECT IDENTIFIER ::=  {fPPrinterStatus 2}

fPSerialStatus OBJECT-TYPE
--  SYNTAX INTEGER {Idle(0), Printing(1), Offline(2)}
   SYNTAX DisplayString (SIZE(0..16))
   ACCESS read-only
   STATUS mandatory
   DESCRIPTION
     "the current serial port status: Idle/Printing/Offline"
   ::= {fPSerial 1}

fPSerialJobs OBJECT-TYPE
--   SYNTAX Counter
   SYNTAX INTEGER
   ACCESS read-write
   STATUS mandatory
   DESCRIPTION
     "the nuber of printed jobs on this Serial port "
   ::= {fPSerial 2}

fPSerialTrigger OBJECT-TYPE
--  SYNTAX INTEGER{Disable(0), Enable(1)}
   SYNTAX DisplayString (SIZE(0..16))
   ACCESS read-write
   STATUS optional
   DESCRIPTION
     " this setting trap when printer is not ready for printing: Enable/Disable"
   ::= {fPSerial 3}


--fPPrintQueue  OBJECT IDENTIFIER ::=  {fPPrinterStatus 3}

--fPQueuePrintedJobs OBJECT-TYPE
--   SYNTAX Counter
--   ACCESS read-write
--   STATUS mandatory
--   DESCRIPTION
--     "the number of printed jobs sent to the print queue "
--   ::= {fPPrintQueue 1}

--fPQueueFailedJobs OBJECT-TYPE
--   SYNTAX Counter
--   ACCESS read-write
--   STATUS mandatory
--   DESCRIPTION
--     "the number of failed jobs sent to the print queue"
--   ::= {fPPrintQueue 2}

--fPQueueTrigger OBJECT-TYPE
--   SYNTAX INTEGER{Disable(0), Enable(1)}
--   ACCESS read-write
--   STATUS mandatory
--   DESCRIPTION
--     " this setting enables trap when net queue printing is failed"
--   ::= {fPPrintQueue 3}


--fPQueueTriggerLimit OBJECT-TYPE
--   SYNTAX INTEGER(0..100)
--   ACCESS read-write
--   STATUS mandatory
--   DESCRIPTION
--     "the percentage of failed jobs which triggers TRAP"
--   ::= {fPPrintQueue 4}


-- FaxPress internet group
fPInternetInfo    OBJECT IDENTIFIER ::=  {faxServer 8}

fPIROutputJobs OBJECT-TYPE
--   SYNTAX Counter
   SYNTAX INTEGER
   ACCESS read-write
   STATUS mandatory
   DESCRIPTION
       "the number of output jobs through Internet routing"
   ::= {fPInternetInfo 1}

fPIRInputJobs OBJECT-TYPE
--   SYNTAX Counter
   SYNTAX INTEGER
   ACCESS read-write
   STATUS mandatory
   DESCRIPTION
       "the number of input jobs through Internet routing"
   ::= {fPInternetInfo 2}

fPIRFailedOutputJobs OBJECT-TYPE
--   SYNTAX Counter
   SYNTAX INTEGER
   ACCESS read-write
   STATUS mandatory
   DESCRIPTION
       "the number of failed output jobs through Internet routing"
   ::= {fPInternetInfo 3}

fPIRFailedInputJobs OBJECT-TYPE
--   SYNTAX Counter
   SYNTAX INTEGER
   ACCESS read-write
   STATUS mandatory
   DESCRIPTION
       "the number of failed Input jobs through Internet routing"
   ::= {fPInternetInfo 4}

--fPIRTrigger OBJECT-TYPE
--   SYNTAX INTEGER {Disable(0), Enable(1)}
--   ACCESS read-write
--   STATUS mandatory
--   DESCRIPTION
--       "Trap trigger setting"
--   ::= {fPInternetInfo 5}

--fPIROutputTriggerLimit OBJECT-TYPE
--   SYNTAX INTEGER(0..100)
--   ACCESS read-write
--   STATUS mandatory
--   DESCRIPTION
--       "the percent of failed output internet jobs to trigger Trap"
--   ::= {fPInternetInfo 6}

--fPIRInputTriggerLimit OBJECT-TYPE
--   SYNTAX INTEGER(0..100)
--   ACCESS read-write
--   STATUS mandatory
--   DESCRIPTION
--       "the percent of failed input internet jobs to trigger Trap"
--   ::= {fPInternetInfo 7}

fPInternetTable OBJECT-TYPE
   SYNTAX SEQUENCE OF FPInternetEntry
   ACCESS not-accessible
   STATUS mandatory
   DESCRIPTION
     "The castelle internet fax setting entry"
   ::= {fPInternetInfo 8}

fPInternetEntry OBJECT-TYPE
   SYNTAX FPInternetEntry
   ACCESS not-accessible
   STATUS mandatory
   DESCRIPTION
      "one entry in castelle internet fax setting table"
   INDEX {fPIRIndex}
   ::= {fPInternetTable 1}

FPInternetEntry ::=
   SEQUENCE {
   fPIRIndex
     INTEGER,
   fPIRPhoneNum
     DisplayString,
   fPIRIpAddr
     IpAddress
	 }


fPIRIndex OBJECT-TYPE
   SYNTAX INTEGER
   ACCESS read-only
   STATUS mandatory
   DESCRIPTION
      "A unique vale for each Internet node."
   ::= {fPInternetEntry 1}

fPIRPhoneNum OBJECT-TYPE
   SYNTAX DisplayString (SIZE(0..48))
   ACCESS read-only
   STATUS mandatory
   DESCRIPTION
       "The destination phone number"
   ::= {fPInternetEntry 2}


fPIRIpAddress OBJECT-TYPE
   SYNTAX IpAddress
   ACCESS read-only
   STATUS mandatory
   DESCRIPTION
       " the corresponding target faxpress IP address"
   ::= {fPInternetEntry 3}


-- SNMP infomation group
fPSnmpInfo     OBJECT IDENTIFIER ::=  {faxServer 9}


fPGetCommunity OBJECT-TYPE
   SYNTAX DisplayString (SIZE(0..24))
   ACCESS read-write
   STATUS mandatory
   DESCRIPTION
       "The Get Community Name"
   ::= {fPSnmpInfo 1}


fPSetCommunity OBJECT-TYPE
   SYNTAX DisplayString (SIZE(0..24))
   ACCESS read-write
   STATUS mandatory
   DESCRIPTION
       "The Set Community Name"
   ::= {fPSnmpInfo 2}


--fPSnmpAuth OBJECT-TYPE
--   SYNTAX INTEGER
--   ACCESS read-write
--   STATUS mandatory
--   DESCRIPTION
--      "The Authority trap flag"
--   ::= {fPSnmpInfo 3}


fPTrapFlag OBJECT-TYPE
   SYNTAX INTEGER {Disable(0), Enable(1)}
   ACCESS read-write
   STATUS mandatory
   DESCRIPTION
      "A Flag for enable/disable trap: 0-Disable 1-Enable"
   ::= {fPSnmpInfo 3}


fPTrapTable OBJECT-TYPE
   SYNTAX SEQUENCE OF FPTrapEntry
   ACCESS not-accessible
   STATUS mandatory
   DESCRIPTION
     "The trap configuration table"
   ::= {fPSnmpInfo 5}



fPTrapEntry OBJECT-TYPE
   SYNTAX FPTrapEntry
   ACCESS not-accessible
   STATUS mandatory
   DESCRIPTION
      "one entry in trap configuration map table"
   INDEX {fPTrapIndex}
   ::= {fPTrapTable 1}


FPTrapEntry ::=
   SEQUENCE {
   fPTrapIndex
     INTEGER,
   fPTrapAddr
     IpAddress,
   fPTrapCommunity
     DisplayString
   }


fPTrapIndex OBJECT-TYPE
   SYNTAX INTEGER
   ACCESS read-only
   STATUS mandatory
   DESCRIPTION
      "A unique vale for each trap."
   ::= {fPTrapEntry 1}



fPTrapAddr OBJECT-TYPE
   SYNTAX IpAddress
   ACCESS read-write
   STATUS mandatory
   DESCRIPTION
       "Trap target Internet Address"
   ::= {fPTrapEntry 2}


fPTrapCommunity OBJECT-TYPE
   SYNTAX DisplayString (SIZE(0..24))
   ACCESS read-write
   STATUS mandatory
   DESCRIPTION
       "Trap Community name"
   ::= {fPTrapEntry 3}


-- Reset infomation group
fPResetInfo     OBJECT IDENTIFIER ::=  {faxServer 10}

fPReboot OBJECT-TYPE
   SYNTAX INTEGER{notReboot(0), reboot(1)}
   ACCESS read-write
   STATUS mandatory
   DESCRIPTION
       "Be careful, this will reboot Faxpress"
   ::= {fPResetInfo 1}


-- Enterprise-specific traps for use with the SNMP-based
-- Network Management Service.

-- Trap definitions that follow are specified compliant with the
-- SMI RFC1155, as amended by the extensions specified
-- for concise MIB specifications RFC1212 and using the conventions for
-- defining event notifications RFC1215.


--  fPBootTrap TRAP-TYPE
--    ENTERPRISE castelle
--    VARIABLES  { fPSystemName, fPLocation }
--    DESCRIPTION
--      "A Faxpress is booting up to services"
--    ::= 1


--  fPFailedJobTrap TRAP-TYPE
--    ENTERPRISE castelle
--    VARIABLES  { fPSystemName, fPLocation, fPOutputJobs, fPFailedJobs }
--    DESCRIPTION
--      "the percentage of failed jobs is over pre-set limit"
--    ::= 2


--  fPOutputTrap TRAP-TYPE
--    ENTERPRISE castelle
--    VARIABLES  { fPSystemName, fPLocation, fPOutputJobsInQueue }
--    DESCRIPTION
--      "the number of jobs in outgoing queue is over pre-set limit"
--    ::= 3

  fPLineTrap TRAP-TYPE
    ENTERPRISE castelle
    VARIABLES  { fPSystemName, fPLocation, fPLineIndex}
    DESCRIPTION
      "the percentage of calls through this line is over pre-set limit"
    ::= 1

  fPParaTrap TRAP-TYPE
    ENTERPRISE castelle
    VARIABLES  { fPSystemName, fPLocation, fPParaStatus }
    DESCRIPTION
      " Parallel printer is in abnormal status -- offline, paperout .."
    ::= 2

  fPSerialTrap TRAP-TYPE
    ENTERPRISE castelle
    VARIABLES  { fPSystemName, fPLocation, fPSerialStatus }
    DESCRIPTION
      " Serial port printer is in abnormal status --offline, paperout .."
    ::= 3

--  fPQueueTrap TRAP-TYPE
--    ENTERPRISE castelle
--    VARIABLES  { fPSystemName, fPLocation, fPQueueJobs, fPFailedQueueJobs }
--    DESCRIPTION
--      "the percentage of failed print queue jobs is over pre-set limit"
--   ::= 7

--  fPIRFailedOutputJobsTrap TRAP-TYPE
--    ENTERPRISE castelle
--    VARIABLES  { fPSystemName, fPLocation, fPIROutputJobs, fPIRFailedOutputJobs }
--    DESCRIPTION
--      "percentage of failed internet output jobs is over pre-set limit"
--    ::= 8

--  fPIRFailedInputJobsTrap TRAP-TYPE
--    ENTERPRISE castelle
--    VARIABLES  { fPSystemName, fPLocation, fPIRInputJobs, fPIRFailedInputJobs }
--    DESCRIPTION
--      "percentage of failed internet input jobs is over pre-set limit"
--    ::= 9

END
