--
-- arymgr.mib
-- MIB generated by MG-SOFT Visual MIB Builder Version 4.0 Build 349
-- Wednesday, November 12, 2003 at 16:01:00
--

-- Copyright (c) 1999-2002 Dell
-- Module Name: arymgr.mib
-- Abstract:
-- 	Defines the Dell OpenManage Array Manager SNMP interface.
-- Authors:
--
-- Revision History:
-- ND  (8/30/99) 0.1 - Original draft
-- ND  (12/3/99) 0.2 - Expanded the trap list by adding the Perc2Provider alerts
-- ND  (1/28/00) 0.3 - Added the arrayMgrGlobalStatus variable
-- GM  (4/25/00) 0.4 - Changed MIB OID from 10890.7 to 10893.1.1
-- GM  (5/25/00) 0.5 - Added several new variables
-- GM  (11/29/00) 0.6 - Added two variables and 660F trap defs.
-- KEMR (03/08/01) 0.7 - Rearranged comments to satisfy format necessary for MG-SOFT MibBuilder
-- KEMR      2.0 - 3.1  Release
-- KEMR      2.0 - 3.1.1 Release
-- KEMR      2.1 - 3.1.2 Release
-- KEMR      2.1 - 3.1.3 Release
-- KEMR      2.2 - 3.2  Release
-- KEMR      2.3 - 3.3.0 Release
-- KEMR      2.3 - 3.4.0 Release
-- KEMR      2.3 - 3.5.0 Release
--
-- Note: Keep these trap numbers reserved for the diagnostics events -
-- 620-649; 652-667. There are currently events using these numbers,
-- but traps were not added to support these.
-- Array Manager release 3.5.
--
-- IMPORTANT NOTE
-- MG-SOFT MibBuilder will be used as the tool to change this MIB. Becuase of the way the MG-SOFT MIB tools work, a copy
-- of the intermediate file with the extension .bui will be kept in SourceSafe along with the ASCII .mib version. When
-- any changes are made to the MIB they will have to be made to the .bui file using MibBuilder and then exported to the
-- .mib file. If you open the .mib version of the MIB in MibBuilder, the compiler is run in on the fly and ALL comments
-- will be removed. This is a "feature" of the tool and is beyond our control.
--

	ArrayManager-MIB DEFINITIONS ::= BEGIN

		IMPORTS
			OBJECT-TYPE
				FROM RFC-1212
			TRAP-TYPE
				FROM RFC-1215
			enterprises
				FROM RFC1155-SMI
			DisplayString
				FROM RFC1213-MIB;



--
-- Node definitions
--

		-- 1.3.6.1.4.1.674
		dell OBJECT IDENTIFIER ::= { enterprises 674 }


		-- 1.3.6.1.4.1.674.10893
		storage OBJECT IDENTIFIER ::= { dell 10893 }


		-- 1.3.6.1.4.1.674.10893.1
		software OBJECT IDENTIFIER ::= { storage 1 }


		-- 1.3.6.1.4.1.674.10893.1.1
		arrayManager OBJECT IDENTIFIER ::= { software 1 }


		-- 1.3.6.1.4.1.674.10893.1.1.1
		arrayMgrSoftwareVersion OBJECT-TYPE
			SYNTAX DisplayString (SIZE (1..32))
			ACCESS read-only
			STATUS mandatory
			DESCRIPTION
				"Version information for the Dell OpenManage
				Array Manager software."
			::= { arrayManager 1 }


		-- 1.3.6.1.4.1.674.10893.1.1.2
		arrayMgrGlobalStatus OBJECT-TYPE
			SYNTAX INTEGER
				{
				critical(1),
				warning(2),
				normal(3),
				unknown(4)
				}
			ACCESS read-only
			STATUS mandatory
			DESCRIPTION
				"Global health information for the subsystem managed by
				the Dell Array Manager software. This global status is
				customized for HP OpenView. Other applications should
				refer to the agentSystemGlobalStatus entry in the
				globalData object group.

				Possible values:
				1: Critical
				2: Warning
				3: Normal
				4: Unknown"
			::= { arrayManager 2 }


		-- 1.3.6.1.4.1.674.10893.1.1.3
		arrayMgrSoftwareManufacturer OBJECT-TYPE
			SYNTAX DisplayString (SIZE (1..32))
			ACCESS read-only
			STATUS mandatory
			DESCRIPTION
				"Manufacturer information for the Dell
				Array Manager software."
			::= { arrayManager 3 }


		-- 1.3.6.1.4.1.674.10893.1.1.4
		arrayMgrSoftwareProduct OBJECT-TYPE
			SYNTAX DisplayString (SIZE (1..64))
			ACCESS read-only
			STATUS mandatory
			DESCRIPTION
				"Product information for the Dell
				Array Manager software."
			::= { arrayManager 4 }


		-- 1.3.6.1.4.1.674.10893.1.1.5
		arrayMgrSoftwareDescription OBJECT-TYPE
			SYNTAX DisplayString (SIZE (1..128))
			ACCESS read-only
			STATUS mandatory
			DESCRIPTION
				"Product Description for the Dell
				Array Manager software."
			::= { arrayManager 5 }


-- This group and all of its associated objects are not
-- supported on Microsoft Windows .NET 64-bit on a PE7150.
		-- 1.3.6.1.4.1.674.10893.1.1.100
		arrayMgrInfo OBJECT IDENTIFIER ::= { arrayManager 100 }


		-- 1.3.6.1.4.1.674.10893.1.1.100.1
		arrayMgrDisplayName OBJECT-TYPE
			SYNTAX DisplayString
			ACCESS read-only
			STATUS mandatory
			DESCRIPTION
				"Name of this agent for display purposes."
			::= { arrayMgrInfo 1 }


		-- 1.3.6.1.4.1.674.10893.1.1.100.2
		arrayMgrDescription OBJECT-TYPE
			SYNTAX DisplayString
			ACCESS read-only
			STATUS mandatory
			DESCRIPTION
				"A short description of this agent such as
				&lt;The Dell Storage Consolidation SNMP Agent&gt;."
			::= { arrayMgrInfo 2 }


		-- 1.3.6.1.4.1.674.10893.1.1.100.3
		arrayMgrAgentVendor OBJECT-TYPE
			SYNTAX DisplayString
			ACCESS read-only
			STATUS mandatory
			DESCRIPTION
				"The name of the agent software manufacturer."
			::= { arrayMgrInfo 3 }


		-- 1.3.6.1.4.1.674.10893.1.1.100.4
		arrayMgrAgentVersion OBJECT-TYPE
			SYNTAX DisplayString
			ACCESS read-only
			STATUS mandatory
			DESCRIPTION
				"Version information for the Dell OpenManage
				Array Manager software."
			::= { arrayMgrInfo 4 }


-- This group and all of its associated objects are not
-- supported on Microsoft Windows .NET 64-bit on a PE7150.
		-- 1.3.6.1.4.1.674.10893.1.1.110
		globalData OBJECT IDENTIFIER ::= { arrayManager 110 }


		-- 1.3.6.1.4.1.674.10893.1.1.110.1
		agentSystemGlobalStatus OBJECT-TYPE
			SYNTAX INTEGER
				{
				normal(1),
				warning(2),
				nonCriticalError(3),
				failure(4),
				unknown(5)
				}
			ACCESS read-only
			STATUS mandatory
			DESCRIPTION
				"Global health information for the subsystem managed by
				the Dell Array Manager software. This global status
				should be used by applications other than HP OpenView.
				HP OpenView should refer to the arrayMgrGlobalStatus in
				the root level object group.
				This is a rollup for the entire agent including any
				monitored devices. The status is intended to give
				initiative to a snmp monitor to get further data when
				this status is abnormal.

				Possible values:
				1: Normal
				2: Warning
				3: Non-critical Error
				4: Failure
				5: Unknown"
			::= { globalData 1 }


		-- 1.3.6.1.4.1.674.10893.1.1.110.2
		agentLastGlobalStatus OBJECT-TYPE
			SYNTAX INTEGER
				{
				normal(1),
				warning(2),
				nonCriticalError(3),
				failure(4),
				unknown(5)
				}
			ACCESS read-only
			STATUS mandatory
			DESCRIPTION
				"The the previous global status of the system managed by the
				Dell Array Manager software.

				Possible values:
				1: Normal
				2: Warning
				3: Non-critical Error
				4: Failure
				5: Unknown"
			::= { globalData 2 }


		-- 1.3.6.1.4.1.674.10893.1.1.110.3
		agentTimeStamp OBJECT-TYPE
			SYNTAX INTEGER
			ACCESS read-only
			STATUS mandatory
			DESCRIPTION
				"The last time that the agent values have been updated.
				Universal time in sec since UTC 1/1/70."
			::= { globalData 3 }


		-- 1.3.6.1.4.1.674.10893.1.1.110.4
		agentGetTimeout OBJECT-TYPE
			SYNTAX INTEGER (1..10000)
			ACCESS read-only
			STATUS mandatory
			DESCRIPTION
				"Suggested timeout value in milliseconds for how long the
				SNMP getter should wait while attempting to poll the SNMP
				agent."
			::= { globalData 4 }


		-- 1.3.6.1.4.1.674.10893.1.1.110.5
		agentModifiers OBJECT-TYPE
			SYNTAX INTEGER (1..10000)
			ACCESS read-only
			STATUS mandatory
			DESCRIPTION
				"Agent functional modifiers, when set the modifier is
				active.
				Bit definitions:
				 Bit 3: agent in debug mode.
				 All other bits are product specific
				"
			::= { globalData 5 }


		-- 1.3.6.1.4.1.674.10893.1.1.110.6
		agentRefreshRate OBJECT-TYPE
			SYNTAX INTEGER (1..10000)
			ACCESS read-only
			STATUS mandatory
			DESCRIPTION
				"Rate in seconds at which the agent cached data is being
				updated."
			::= { globalData 6 }


		-- 1.3.6.1.4.1.674.10893.1.1.110.7
		agentHostname OBJECT-TYPE
			SYNTAX DisplayString
			ACCESS read-only
			STATUS mandatory
			DESCRIPTION
				"The fully qualified network hostname of the host where
				the agent is running."
			::= { globalData 7 }


		-- 1.3.6.1.4.1.674.10893.1.1.110.8
		agentIPAddress OBJECT-TYPE
			SYNTAX DisplayString
			ACCESS read-only
			STATUS mandatory
			DESCRIPTION
				"The IP Address of the host where the agent is running and
				at which the SNMP agent can be contacted."
			::= { globalData 8 }


		-- 1.3.6.1.4.1.674.10893.1.1.110.9
		agentSoftwareStatus OBJECT-TYPE
			SYNTAX INTEGER
				{
				databaseUp(1),
				databaseDown(2)
				}
			ACCESS read-only
			STATUS mandatory
			DESCRIPTION
				"Status of the Array Manager Database service software.
				1: Database Up - Communication with the database is possible for SNMP queries.
				2: Database Down - Communication with the database is not possible for SNMP queries."
			::= { globalData 9 }


		-- 1.3.6.1.4.1.674.10893.1.1.110.10
		agentAmSnmpVersion OBJECT-TYPE
			SYNTAX DisplayString
			ACCESS read-only
			STATUS mandatory
			DESCRIPTION
				"Version of the Array Manager SNMP extension agent for
				Windows, SNMP provider for Netware."
			::= { globalData 10 }


		-- 1.3.6.1.4.1.674.10893.1.1.110.11
		agentAmMibVersion OBJECT-TYPE
			SYNTAX DisplayString
			ACCESS read-only
			STATUS mandatory
			DESCRIPTION
				"Version of the Array Manager MIB."
			::= { globalData 11 }


-- This group and all of its associated tables and objects are not
-- supported on Microsoft Windows .NET 64-bit on a PE7150.
		-- 1.3.6.1.4.1.674.10893.1.1.120
		providerData OBJECT IDENTIFIER ::= { arrayManager 120 }


		-- 1.3.6.1.4.1.674.10893.1.1.120.1
		providerTable OBJECT-TYPE
			SYNTAX SEQUENCE OF ProviderEntry
			ACCESS not-accessible
			STATUS mandatory
			::= { providerData 1 }


		-- 1.3.6.1.4.1.674.10893.1.1.120.1.1
		providerEntry OBJECT-TYPE
			SYNTAX ProviderEntry
			ACCESS not-accessible
			STATUS mandatory
			INDEX { providerNumber }
			::= { providerTable 1 }


		ProviderEntry ::=
			SEQUENCE {
				providerNumber
					INTEGER,
				providerName
					DisplayString,
				providerStatus
					INTEGER,
				providerVersion
					DisplayString
			 }

		-- 1.3.6.1.4.1.674.10893.1.1.120.1.1.1
		providerNumber OBJECT-TYPE
			SYNTAX INTEGER (1..255)
			ACCESS read-only
			STATUS mandatory
			DESCRIPTION
				"Instance number of this provider entry."
			::= { providerEntry 1 }


		-- 1.3.6.1.4.1.674.10893.1.1.120.1.1.2
		providerName OBJECT-TYPE
			SYNTAX DisplayString
			ACCESS read-only
			STATUS mandatory
			DESCRIPTION
				"The name of the module that supports either a family of
				devices or a set of functions."
			::= { providerEntry 2 }


		-- 1.3.6.1.4.1.674.10893.1.1.120.1.1.3
		providerStatus OBJECT-TYPE
			SYNTAX INTEGER
				{
				loaded(1),
				failed(2),
				unknown(3)
				}
			ACCESS read-only
			STATUS mandatory
			DESCRIPTION
				"The status of this provider.
				1: Loaded
				2: Failed
				3: Unknown"
			::= { providerEntry 3 }


		-- 1.3.6.1.4.1.674.10893.1.1.120.1.1.4
		providerVersion OBJECT-TYPE
			SYNTAX DisplayString
			ACCESS read-only
			STATUS mandatory
			DESCRIPTION
				"This version and build number of the provider module."
			::= { providerEntry 4 }


-- This group and all of its associated tables and objects are not
-- supported on Microsoft Windows .NET 64-bit on a PE7150.
		-- 1.3.6.1.4.1.674.10893.1.1.130
		physicalDevices OBJECT IDENTIFIER ::= { arrayManager 130 }


		-- 1.3.6.1.4.1.674.10893.1.1.130.1
		controllerTable OBJECT-TYPE
			SYNTAX SEQUENCE OF ControllerEntry
			ACCESS not-accessible
			STATUS mandatory
			DESCRIPTION
				"A table of managed RAID controllers. The number of entries
				is related to number of RAID controllers discovered in the
				system."
			::= { physicalDevices 1 }


		-- 1.3.6.1.4.1.674.10893.1.1.130.1.1
		controllerEntry OBJECT-TYPE
			SYNTAX ControllerEntry
			ACCESS not-accessible
			STATUS mandatory
			DESCRIPTION
				"An entry in the table of RAID controllers. A row in this table cannot
				be created or deleted by SNMP operations on columns of the table."
			INDEX { controllerNumber }
			::= { controllerTable 1 }


		ControllerEntry ::=
			SEQUENCE {
				controllerNumber
					INTEGER,
				controllerName
					DisplayString,
				controllerVendor
					DisplayString,
				controllerType
					INTEGER,
				controllerState
					INTEGER,
				controllerSeverity
					INTEGER,
				controllerRebuildRateInPercent
					INTEGER,
				controllerFWVersion
					DisplayString,
				controllerCacheSizeInMB
					INTEGER,
				controllerCacheSizeInBytes
					INTEGER,
				controllerPhysicalDeviceCount
					INTEGER,
				controllerLogicalDeviceCount
					INTEGER,
				controllerPartnerStatus
					DisplayString,
				controllerHostPortCount
					INTEGER,
				controllerMemorySizeInMB
					INTEGER,
				controllerMemorySizeInBytes
					INTEGER,
				controllerDriveChannelCount
					INTEGER,
				controllerFaultTolerant
					INTEGER,
				controllerC0Port0WWN
					DisplayString,
				controllerC0Port0Name
					DisplayString,
				controllerC0Port0ID
					INTEGER,
				controllerC0Target
					INTEGER,
				controllerC0Channel
					INTEGER,
				controllerC0OSController
					DisplayString,
				controllerC0BatteryState
					INTEGER,
				controllerC1Port0WWN
					DisplayString,
				controllerC1Port0Name
					DisplayString,
				controllerC1Port0ID
					INTEGER,
				controllerC1Target
					INTEGER,
				controllerC1Channel
					INTEGER,
				controllerC1OSController
					INTEGER,
				controllerC1BatteryState
					INTEGER,
				controllerNodeWWN
					DisplayString,
				controllerC0Port1WWN
					DisplayString,
				controllerC1Port1WWN
					DisplayString,
				controllerBatteryChargeCount
					INTEGER
			 }

		-- 1.3.6.1.4.1.674.10893.1.1.130.1.1.1
		controllerNumber OBJECT-TYPE
			SYNTAX INTEGER (1..255)
			ACCESS read-only
			STATUS mandatory
			DESCRIPTION
				"Instance number of this controller entry."
			::= { controllerEntry 1 }


		-- 1.3.6.1.4.1.674.10893.1.1.130.1.1.2
		controllerName OBJECT-TYPE
			SYNTAX DisplayString
			ACCESS read-only
			STATUS mandatory
			DESCRIPTION
				"The name of the contoller in this subsystem as represented in
				Array Manager.
				Includes the controller type and instance.
				For example: Perc3/QC 1."
			::= { controllerEntry 2 }


		-- 1.3.6.1.4.1.674.10893.1.1.130.1.1.3
		controllerVendor OBJECT-TYPE
			SYNTAX DisplayString
			ACCESS read-only
			STATUS mandatory
			DESCRIPTION
				"The controller's (re)seller's name. For Dell controllers this
				will = Dell."
			::= { controllerEntry 3 }


		-- 1.3.6.1.4.1.674.10893.1.1.130.1.1.4
		controllerType OBJECT-TYPE
			SYNTAX INTEGER
				{
				scsi(1),
				pv660F(2),
				pv662F(3),
				ide(4)
				}
			ACCESS read-only
			STATUS mandatory
			DESCRIPTION
				"The type of this controller:
				1: SCSI
				2: PV660F
				3: PV662F
				4: IDE (Integrated/Intelligent Drive Electronics)"
			::= { controllerEntry 4 }


		-- 1.3.6.1.4.1.674.10893.1.1.130.1.1.5
		controllerState OBJECT-TYPE
			SYNTAX INTEGER
				{
				ready(1),
				failed(2),
				online(3),
				offline(4),
				degraded(6)
				}
			ACCESS read-only
			STATUS mandatory
			DESCRIPTION
				"The status of this controller's subsystem
				(which includes any devices connected to it.)
				Possible states:
				0: Unknown
				1: Ready
				2: Failed
				3: Online
				4: Offline
				6: Degraded"
			::= { controllerEntry 5 }


		-- 1.3.6.1.4.1.674.10893.1.1.130.1.1.6
		controllerSeverity OBJECT-TYPE
			SYNTAX INTEGER
				{
				warning(1),
				error(2),
				failure(3)
				}
			ACCESS read-only
			STATUS mandatory
			DESCRIPTION
				"Seriousness of the controller state.
				Possible values:
				0: OK
				1: Warning
				2: Error
				3: Failure"
			::= { controllerEntry 6 }


		-- 1.3.6.1.4.1.674.10893.1.1.130.1.1.7
		controllerRebuildRateInPercent OBJECT-TYPE
			SYNTAX INTEGER (0..100)
			ACCESS read-only
			STATUS mandatory
			DESCRIPTION
				"The percent of the compute cycles dedicated to rebuilding
				failed array disks. "
			::= { controllerEntry 7 }


		-- 1.3.6.1.4.1.674.10893.1.1.130.1.1.8
		controllerFWVersion OBJECT-TYPE
			SYNTAX DisplayString
			ACCESS read-only
			STATUS mandatory
			DESCRIPTION
				"The controller's current firmware version."
			::= { controllerEntry 8 }


		-- 1.3.6.1.4.1.674.10893.1.1.130.1.1.9
		controllerCacheSizeInMB OBJECT-TYPE
			SYNTAX INTEGER
			ACCESS read-only
			STATUS mandatory
			DESCRIPTION
				"The controller's current amount of cache memory in
				megabytes. If this size is 0, it is less than a
				megabyte."
			::= { controllerEntry 9 }


		-- 1.3.6.1.4.1.674.10893.1.1.130.1.1.10
		controllerCacheSizeInBytes OBJECT-TYPE
			SYNTAX INTEGER
			ACCESS read-only
			STATUS mandatory
			DESCRIPTION
				"The controller's current amount of cache memory that is
				less than a megabyte. This combined with the
				controllerCacheSizeInMB will be the total amount of
				memory."
			::= { controllerEntry 10 }


		-- 1.3.6.1.4.1.674.10893.1.1.130.1.1.11
		controllerPhysicalDeviceCount OBJECT-TYPE
			SYNTAX INTEGER
			ACCESS read-only
			STATUS mandatory
			DESCRIPTION
				"Number of physical devices on the controller channel including
				both disks and the controller."
			::= { controllerEntry 11 }


		-- 1.3.6.1.4.1.674.10893.1.1.130.1.1.12
		controllerLogicalDeviceCount OBJECT-TYPE
			SYNTAX INTEGER
			ACCESS read-only
			STATUS mandatory
			DESCRIPTION
				"Number of virtual disks on the controller."
			::= { controllerEntry 12 }


		-- 1.3.6.1.4.1.674.10893.1.1.130.1.1.13
		controllerPartnerStatus OBJECT-TYPE
			SYNTAX DisplayString
			ACCESS read-only
			STATUS mandatory
			DESCRIPTION
				"Indicates availability of the redundant controller in a
				redundant configuration.

				Booting: Controller is powering up.
				OK:    Controller is in fully redundant status.
				Inserted: Controller is there, but not acting as a partner.
				Kill Partner Command Received:
				Failed:
				UnknownStatus:
				SCSI Comm Failure:"
			::= { controllerEntry 13 }


		-- 1.3.6.1.4.1.674.10893.1.1.130.1.1.14
		controllerHostPortCount OBJECT-TYPE
			SYNTAX INTEGER
			ACCESS read-only
			STATUS mandatory
			DESCRIPTION
				"The number of host ports on this controller.
				Host Port: An active fibre port connected to an arbitrated
				loop. The port may be opened by an initiator on the loop
				and process i/o requests.
				"
			::= { controllerEntry 14 }


		-- 1.3.6.1.4.1.674.10893.1.1.130.1.1.15
		controllerMemorySizeInMB OBJECT-TYPE
			SYNTAX INTEGER
			ACCESS read-only
			STATUS mandatory
			DESCRIPTION
				"Size of memory in megabytes on the controller. If this
				size is 0, it is less than a megabyte."
			::= { controllerEntry 15 }


		-- 1.3.6.1.4.1.674.10893.1.1.130.1.1.16
		controllerMemorySizeInBytes OBJECT-TYPE
			SYNTAX INTEGER
			ACCESS read-only
			STATUS mandatory
			DESCRIPTION
				"Size of memory on the controller that is less than a
				megabyte. This combined with the controllerMemorySizeInMB
				will be the total size of the memory."
			::= { controllerEntry 16 }


		-- 1.3.6.1.4.1.674.10893.1.1.130.1.1.17
		controllerDriveChannelCount OBJECT-TYPE
			SYNTAX INTEGER (1..4)
			ACCESS read-only
			STATUS mandatory
			DESCRIPTION
				"The number of redundant drive channels for the controller."
			::= { controllerEntry 17 }


		-- 1.3.6.1.4.1.674.10893.1.1.130.1.1.18
		controllerFaultTolerant OBJECT-TYPE
			SYNTAX INTEGER { yes(1) }
			ACCESS read-only
			STATUS mandatory
			DESCRIPTION
				"Indicates whether the controller is enabled to be
				fault tolerant.
				0: no
				1: yes
				"
			::= { controllerEntry 18 }


		-- 1.3.6.1.4.1.674.10893.1.1.130.1.1.19
		controllerC0Port0WWN OBJECT-TYPE
			SYNTAX DisplayString
			ACCESS read-only
			STATUS mandatory
			DESCRIPTION
				"World Wide name for the first port on controller 0.
				"
			::= { controllerEntry 19 }


		-- 1.3.6.1.4.1.674.10893.1.1.130.1.1.20
		controllerC0Port0Name OBJECT-TYPE
			SYNTAX DisplayString
			ACCESS read-only
			STATUS mandatory
			DESCRIPTION
				"The unique value/name assigned to the controller's first
				active port."
			::= { controllerEntry 20 }


		-- 1.3.6.1.4.1.674.10893.1.1.130.1.1.21
		controllerC0Port0ID OBJECT-TYPE
			SYNTAX INTEGER
			ACCESS read-only
			STATUS mandatory
			DESCRIPTION
				"The controller's preferred host port/loopid as specified
				by controller option 'hard loop id' for its first port."
			::= { controllerEntry 21 }


		-- 1.3.6.1.4.1.674.10893.1.1.130.1.1.22
		controllerC0Target OBJECT-TYPE
			SYNTAX INTEGER
			ACCESS read-only
			STATUS mandatory
			DESCRIPTION
				"The controller in slot 0 (it should always be the master
				controller.)
				"
			::= { controllerEntry 22 }


		-- 1.3.6.1.4.1.674.10893.1.1.130.1.1.23
		controllerC0Channel OBJECT-TYPE
			SYNTAX INTEGER
			ACCESS read-only
			STATUS mandatory
			DESCRIPTION
				"Channel number of the controller's first port.
				Channel: A path for the transfer of data and controller
				information between the host or the physical disk drives
				and the controller."
			::= { controllerEntry 23 }


		-- 1.3.6.1.4.1.674.10893.1.1.130.1.1.24
		controllerC0OSController OBJECT-TYPE
			SYNTAX DisplayString
			ACCESS read-only
			STATUS mandatory
			DESCRIPTION
				"Manufacturer's identification of controller on first port."
			::= { controllerEntry 24 }


		-- 1.3.6.1.4.1.674.10893.1.1.130.1.1.25
		controllerC0BatteryState OBJECT-TYPE
			SYNTAX INTEGER
				{
				ok(1),
				failed(2),
				reconditioning(7),
				high(9),
				low(10),
				charging(12),
				missing(21)
				}
			ACCESS read-only
			STATUS mandatory
			DESCRIPTION
				"Current state of battery on the controller's first port.
				Possible values:
				 0: Unknown
				 1: OK (present and operational)
				 2: Failed (cannot hold charge or cannot be recharged)
				 7: Reconditioning (PV660 Only)
				 9: High
				10: Low
				12: Charging
				21: Missing (Adaptec Only)

				"
			::= { controllerEntry 25 }


		-- 1.3.6.1.4.1.674.10893.1.1.130.1.1.26
		controllerC1Port0WWN OBJECT-TYPE
			SYNTAX DisplayString
			ACCESS read-only
			STATUS mandatory
			DESCRIPTION
				"World Wide name for the first port on controller 1."
			::= { controllerEntry 26 }


		-- 1.3.6.1.4.1.674.10893.1.1.130.1.1.27
		controllerC1Port0Name OBJECT-TYPE
			SYNTAX DisplayString
			ACCESS read-only
			STATUS mandatory
			DESCRIPTION
				"The unique value/name assigned to the controller's second
				active port."
			::= { controllerEntry 27 }


		-- 1.3.6.1.4.1.674.10893.1.1.130.1.1.28
		controllerC1Port0ID OBJECT-TYPE
			SYNTAX INTEGER
			ACCESS read-only
			STATUS mandatory
			DESCRIPTION
				"The controller's preferred host port/loopid as specified
				by controller option 'hard loop id' for its second port.
				(Value of 255 = C1 controller not there)
				"
			::= { controllerEntry 28 }


		-- 1.3.6.1.4.1.674.10893.1.1.130.1.1.29
		controllerC1Target OBJECT-TYPE
			SYNTAX INTEGER
			ACCESS read-only
			STATUS mandatory
			DESCRIPTION
				"The controller in slot 1.
				(Value of 255 = controller not there)"
			::= { controllerEntry 29 }


		-- 1.3.6.1.4.1.674.10893.1.1.130.1.1.30
		controllerC1Channel OBJECT-TYPE
			SYNTAX INTEGER
			ACCESS read-only
			STATUS mandatory
			DESCRIPTION
				"Channel number of the controller's second port.
				Channel: A path for the transfer of data and controller
				information between the host or the physical disk drives
				and the controller.
				(Value of 255 = controller not there)"
			::= { controllerEntry 30 }


		-- 1.3.6.1.4.1.674.10893.1.1.130.1.1.31
		controllerC1OSController OBJECT-TYPE
			SYNTAX INTEGER
			ACCESS read-only
			STATUS mandatory
			DESCRIPTION
				"Manufacturer's identification of controller on second port.
				(Value of 255 = controller not there)"
			::= { controllerEntry 31 }


		-- 1.3.6.1.4.1.674.10893.1.1.130.1.1.32
		controllerC1BatteryState OBJECT-TYPE
			SYNTAX INTEGER
				{
				ok(1),
				failed(2),
				reconditioning(7),
				high(9),
				low(10),
				charging(12),
				missing(21)
				}
			ACCESS read-only
			STATUS mandatory
			DESCRIPTION
				"Current state of battery on the controller's second port.
				Possible values:
				 0: Unknown
				 1: OK (present and operational)
				 2: Failed (cannot hold charge or cannot be recharged)
				 7: Reconditioning (PV660 Only)
				 9: High
				10: Low
				12: Charging
				21: Missing (Adaptec Only)
				"
			::= { controllerEntry 32 }


		-- 1.3.6.1.4.1.674.10893.1.1.130.1.1.33
		controllerNodeWWN OBJECT-TYPE
			SYNTAX DisplayString
			ACCESS read-only
			STATUS mandatory
			DESCRIPTION
				"Used as the node name for the storage subsystem. "
			::= { controllerEntry 33 }


		-- 1.3.6.1.4.1.674.10893.1.1.130.1.1.34
		controllerC0Port1WWN OBJECT-TYPE
			SYNTAX DisplayString
			ACCESS read-only
			STATUS mandatory
			DESCRIPTION
				"World Wide name for the second port on controller 0."
			::= { controllerEntry 34 }


		-- 1.3.6.1.4.1.674.10893.1.1.130.1.1.35
		controllerC1Port1WWN OBJECT-TYPE
			SYNTAX DisplayString
			ACCESS read-only
			STATUS mandatory
			DESCRIPTION
				"World Wide name for the second port on controller 1."
			::= { controllerEntry 35 }


		-- 1.3.6.1.4.1.674.10893.1.1.130.1.1.36
		controllerBatteryChargeCount OBJECT-TYPE
			SYNTAX INTEGER
			ACCESS read-only
			STATUS mandatory
			DESCRIPTION
				"The number of charges that have been applied to the battery on
				this controller."
			::= { controllerEntry 36 }


		-- 1.3.6.1.4.1.674.10893.1.1.130.2
		channelTable OBJECT-TYPE
			SYNTAX SEQUENCE OF ChannelEntry
			ACCESS not-accessible
			STATUS mandatory
			DESCRIPTION
				"A table of controller channels. The number of entries is
				related to number of channels supported in a RAID
				controllers. Perc2 RAID controller supports a max of 4
				channels per controller. The maximum number of entries is
				implementation dependent."
			::= { physicalDevices 2 }


		-- 1.3.6.1.4.1.674.10893.1.1.130.2.1
		channelEntry OBJECT-TYPE
			SYNTAX ChannelEntry
			ACCESS not-accessible
			STATUS mandatory
			DESCRIPTION
				"An entry in the channel table. A row in this table cannot be
				created or deleted by SNMP operations on columns of the table."
			INDEX { channelNumber }
			::= { channelTable 1 }


		ChannelEntry ::=
			SEQUENCE {
				channelNumber
					INTEGER,
				channelName
					DisplayString,
				channelState
					INTEGER,
				channelSeverity
					INTEGER,
				channelTermination
					INTEGER,
				channelSCSIID
					INTEGER
			 }

		-- 1.3.6.1.4.1.674.10893.1.1.130.2.1.1
		channelNumber OBJECT-TYPE
			SYNTAX INTEGER (1..255)
			ACCESS read-only
			STATUS mandatory
			DESCRIPTION
				"Instance number of this channel entry."
			::= { channelEntry 1 }


		-- 1.3.6.1.4.1.674.10893.1.1.130.2.1.2
		channelName OBJECT-TYPE
			SYNTAX DisplayString
			ACCESS read-only
			STATUS mandatory
			DESCRIPTION
				"The name of the channel as represented in Array Manager.
				The name will include the word channel and the instance.
				For example: Channel 1"
			::= { channelEntry 2 }


		-- 1.3.6.1.4.1.674.10893.1.1.130.2.1.3
		channelState OBJECT-TYPE
			SYNTAX INTEGER
				{
				ready(1),
				failed(2),
				online(3),
				offline(4),
				degraded(6)
				}
			ACCESS read-only
			STATUS mandatory
			DESCRIPTION
				"The current state of this channel.
				Possible states:
				0: Unknown
				1: Ready - The I/O has resumed.
				2: Failed
				3: Online
				4: Offline - The I/O has paused.
				6: Degraded
				"
			::= { channelEntry 3 }


		-- 1.3.6.1.4.1.674.10893.1.1.130.2.1.4
		channelSeverity OBJECT-TYPE
			SYNTAX INTEGER
				{
				warning(1),
				error(2),
				failure(3)
				}
			ACCESS read-only
			STATUS mandatory
			DESCRIPTION
				"Seriousness of the channel state.
				Possible values:
				0: OK
				1: Warning
				2: Error
				3: Failure"
			::= { channelEntry 4 }


		-- 1.3.6.1.4.1.674.10893.1.1.130.2.1.5
		channelTermination OBJECT-TYPE
			SYNTAX INTEGER
				{
				wide(1),
				narrow(2),
				notTerminated(3)
				}
			ACCESS read-only
			STATUS mandatory
			DESCRIPTION
				"The type of SCSI termination on this channel.
				Termination is required for proper operation of this channel.

				1: Wide Termination (16 bit)
				2: Narrow Termination (8 bit)
				3: Not Terminated"
			::= { channelEntry 5 }


		-- 1.3.6.1.4.1.674.10893.1.1.130.2.1.6
		channelSCSIID OBJECT-TYPE
			SYNTAX INTEGER
			ACCESS read-only
			STATUS mandatory
			DESCRIPTION
				"The SCSI ID of the controller to which the channel belongs."
			::= { channelEntry 6 }


		-- 1.3.6.1.4.1.674.10893.1.1.130.3
		enclosureTable OBJECT-TYPE
			SYNTAX SEQUENCE OF EnclosureEntry
			ACCESS not-accessible
			STATUS mandatory
			::= { physicalDevices 3 }


		-- 1.3.6.1.4.1.674.10893.1.1.130.3.1
		enclosureEntry OBJECT-TYPE
			SYNTAX EnclosureEntry
			ACCESS not-accessible
			STATUS mandatory
			INDEX { enclosureNumber }
			::= { enclosureTable 1 }


		EnclosureEntry ::=
			SEQUENCE {
				enclosureNumber
					INTEGER,
				enclosureName
					DisplayString,
				enclosureVendor
					DisplayString,
				enclosureState
					INTEGER,
				enclosureSeverity
					INTEGER,
				enclosureID
					INTEGER,
				enclosureProcessorVersion
					DisplayString,
				enclosureServiceTag
					DisplayString,
				enclosureAssetTag
					DisplayString,
				enclosureAssetName
					DisplayString,
				enclosureSplitBusPartNumber
					DisplayString,
				enclosureProductID
					DisplayString,
				enclosureKernelVersion
					DisplayString,
				enclosureESM1PartNumber
					DisplayString,
				enclosureESM2PartNumber
					DisplayString,
				enclosureType
					INTEGER,
				enclosureProcessor2Version
					DisplayString,
				enclosureConfig
					INTEGER,
				enclosureChannelNumber
					INTEGER,
				enclosureAlarm
					INTEGER,
				enclosureBackplanePartNumber
					DisplayString,
				enclosureSCSIID
					INTEGER
			 }

		-- 1.3.6.1.4.1.674.10893.1.1.130.3.1.1
		enclosureNumber OBJECT-TYPE
			SYNTAX INTEGER (1..255)
			ACCESS read-only
			STATUS mandatory
			DESCRIPTION
				"Instance number of the enclosure entry."
			::= { enclosureEntry 1 }


		-- 1.3.6.1.4.1.674.10893.1.1.130.3.1.2
		enclosureName OBJECT-TYPE
			SYNTAX DisplayString
			ACCESS read-only
			STATUS mandatory
			DESCRIPTION
				"The enclosure's name as represented in Array Manager."
			::= { enclosureEntry 2 }


		-- 1.3.6.1.4.1.674.10893.1.1.130.3.1.3
		enclosureVendor OBJECT-TYPE
			SYNTAX DisplayString
			ACCESS read-only
			STATUS mandatory
			DESCRIPTION
				"The enclosure's (re)seller's name."
			::= { enclosureEntry 3 }


		-- 1.3.6.1.4.1.674.10893.1.1.130.3.1.4
		enclosureState OBJECT-TYPE
			SYNTAX INTEGER
				{
				ready(1),
				failed(2),
				online(3),
				offline(4),
				degraded(6),
				commLost(55)
				}
			ACCESS read-only
			STATUS mandatory
			DESCRIPTION
				"The state of the controller.
				Possible states:
				0 : Unknown
				1 : Ready
				2 : Failed
				3 : Online
				4 : Offline
				6 : Degraded
				55: Communication Lost"
			::= { enclosureEntry 4 }


		-- 1.3.6.1.4.1.674.10893.1.1.130.3.1.5
		enclosureSeverity OBJECT-TYPE
			SYNTAX INTEGER
				{
				warining(1),
				error(2),
				failure(3)
				}
			ACCESS read-only
			STATUS mandatory
			DESCRIPTION
				"Seriousness of the enclosure state.
				Possible values:
				0: OK
				1: Warning
				2: Error
				3: Failure"
			::= { enclosureEntry 5 }


		-- 1.3.6.1.4.1.674.10893.1.1.130.3.1.6
		enclosureID OBJECT-TYPE
			SYNTAX INTEGER
			ACCESS read-only
			STATUS mandatory
			DESCRIPTION
				"For fibre channel - The number of the enclosure in the subsystem.
				For SCSI - The SCSI address of the processor."
			::= { enclosureEntry 6 }


		-- 1.3.6.1.4.1.674.10893.1.1.130.3.1.7
		enclosureProcessorVersion OBJECT-TYPE
			SYNTAX DisplayString
			ACCESS read-only
			STATUS mandatory
			DESCRIPTION
				"Firmware version of the enclosure's processor.
				For Fibre Channel only."
			::= { enclosureEntry 7 }


		-- 1.3.6.1.4.1.674.10893.1.1.130.3.1.8
		enclosureServiceTag OBJECT-TYPE
			SYNTAX DisplayString
			ACCESS read-only
			STATUS mandatory
			DESCRIPTION
				"Enclosure identification used when consulting customer
				support."
			::= { enclosureEntry 8 }


		-- 1.3.6.1.4.1.674.10893.1.1.130.3.1.9
		enclosureAssetTag OBJECT-TYPE
			SYNTAX DisplayString
			ACCESS read-only
			STATUS mandatory
			DESCRIPTION
				"Customer definable asset tag for the enclosure."
			::= { enclosureEntry 9 }


		-- 1.3.6.1.4.1.674.10893.1.1.130.3.1.10
		enclosureAssetName OBJECT-TYPE
			SYNTAX DisplayString
			ACCESS read-only
			STATUS mandatory
			DESCRIPTION
				"Customer definable asset name of the enclosure."
			::= { enclosureEntry 10 }


		-- 1.3.6.1.4.1.674.10893.1.1.130.3.1.11
		enclosureSplitBusPartNumber OBJECT-TYPE
			SYNTAX DisplayString
			ACCESS read-only
			STATUS mandatory
			DESCRIPTION
				"The enclosure's split bus part number."
			::= { enclosureEntry 11 }


		-- 1.3.6.1.4.1.674.10893.1.1.130.3.1.12
		enclosureProductID OBJECT-TYPE
			SYNTAX DisplayString
			ACCESS read-only
			STATUS mandatory
			DESCRIPTION
				"The enclosure's product identification. This also
				corresponds to the enclosure type.
				"
			::= { enclosureEntry 12 }


		-- 1.3.6.1.4.1.674.10893.1.1.130.3.1.13
		enclosureKernelVersion OBJECT-TYPE
			SYNTAX DisplayString
			ACCESS read-only
			STATUS mandatory
			DESCRIPTION
				"The version of the enclosure's kernel (Dell PV200S,
				PV201S, PV210S, and PV211S only.)"
			::= { enclosureEntry 13 }


		-- 1.3.6.1.4.1.674.10893.1.1.130.3.1.14
		enclosureESM1PartNumber OBJECT-TYPE
			SYNTAX DisplayString
			ACCESS read-only
			STATUS mandatory
			DESCRIPTION
				"This entry is obsolete."
			::= { enclosureEntry 14 }


		-- 1.3.6.1.4.1.674.10893.1.1.130.3.1.15
		enclosureESM2PartNumber OBJECT-TYPE
			SYNTAX DisplayString
			ACCESS read-only
			STATUS mandatory
			DESCRIPTION
				"This entry is obsolete."
			::= { enclosureEntry 15 }


		-- 1.3.6.1.4.1.674.10893.1.1.130.3.1.16
		enclosureType OBJECT-TYPE
			SYNTAX INTEGER
				{
				internal(1),
				dELLPV200SPV201S(2),
				dELLPV210SPV211S(3),
				dELLPV220SPV221S(4),
				dELLPV660F(5),
				dELLPV224F(6),
				dELLPV660F224F(7)
				}
			ACCESS read-only
			STATUS mandatory
			DESCRIPTION
				"The type of this enclosure.
				Possible values:
				1: Internal
				2: Dell PV200S (PV201S)
				3: Dell PV210S (PV211S)
				4: Dell PV220S (PV221S)
				5: Dell PV660F
				6: Dell PV224F
				7: Dell PV660F / PV224F"
			::= { enclosureEntry 16 }


		-- 1.3.6.1.4.1.674.10893.1.1.130.3.1.17
		enclosureProcessor2Version OBJECT-TYPE
			SYNTAX DisplayString
			ACCESS read-only
			STATUS mandatory
			DESCRIPTION
				"This entry is obsolete."
			::= { enclosureEntry 17 }


		-- 1.3.6.1.4.1.674.10893.1.1.130.3.1.18
		enclosureConfig OBJECT-TYPE
			SYNTAX INTEGER
				{
				joined(1),
				splitBus(2),
				clustered(3)
				}
			ACCESS read-only
			STATUS mandatory
			DESCRIPTION
				"The current configuration of the enclosure's backplane.
				Possible values:
				1: Joined
				2: Split Bus
				3: Clustered"
			::= { enclosureEntry 18 }


		-- 1.3.6.1.4.1.674.10893.1.1.130.3.1.19
		enclosureChannelNumber OBJECT-TYPE
			SYNTAX INTEGER
			ACCESS read-only
			STATUS mandatory
			DESCRIPTION
				"The channel number, or bus, to which the enclosure is
				connected."
			::= { enclosureEntry 19 }


		-- 1.3.6.1.4.1.674.10893.1.1.130.3.1.20
		enclosureAlarm OBJECT-TYPE
			SYNTAX INTEGER
				{
				off(1),
				on(2)
				}
			ACCESS read-only
			STATUS mandatory
			DESCRIPTION
				"The current status of the enclosure's alarm
				(PV220S, and PV221S only.)
				Possible values:
				1: Off
				2: On"
			::= { enclosureEntry 20 }


		-- 1.3.6.1.4.1.674.10893.1.1.130.3.1.21
		enclosureBackplanePartNumber OBJECT-TYPE
			SYNTAX DisplayString
			ACCESS read-only
			STATUS mandatory
			DESCRIPTION
				"The part number of the enclosure's backplane."
			::= { enclosureEntry 21 }


		-- 1.3.6.1.4.1.674.10893.1.1.130.3.1.22
		enclosureSCSIID OBJECT-TYPE
			SYNTAX INTEGER
			ACCESS read-only
			STATUS mandatory
			DESCRIPTION
				"The SCSI ID of the controller to which this enclosure is attached."
			::= { enclosureEntry 22 }


		-- 1.3.6.1.4.1.674.10893.1.1.130.4
		arrayDiskTable OBJECT-TYPE
			SYNTAX SEQUENCE OF ArrayDiskEntry
			ACCESS not-accessible
			STATUS mandatory
			DESCRIPTION
				"A table of managed Array Disks. The number of entries is
				related to number of Array Disks discovered in the system.
				The maximum number of entries is implementation dependent."
			::= { physicalDevices 4 }


		-- 1.3.6.1.4.1.674.10893.1.1.130.4.1
		arrayDiskEntry OBJECT-TYPE
			SYNTAX ArrayDiskEntry
			ACCESS not-accessible
			STATUS mandatory
			DESCRIPTION
				"An entry in the Array Disk table . A row in this table cannot be
				created or deleted by SNMP operations on columns of the table."
			INDEX { arrayDiskNumber }
			::= { arrayDiskTable 1 }


		ArrayDiskEntry ::=
			SEQUENCE {
				arrayDiskNumber
					INTEGER,
				arrayDiskName
					DisplayString,
				arrayDiskVendor
					DisplayString,
				arrayDiskState
					INTEGER,
				arrayDiskSeverity
					INTEGER,
				arrayDiskProductID
					DisplayString,
				arrayDiskSerialNo
					DisplayString,
				arrayDiskRevision
					DisplayString,
				arrayDiskEnclosureID
					DisplayString,
				arrayDiskChannel
					INTEGER,
				arrayDiskLengthInMB
					INTEGER,
				arrayDiskLengthInBytes
					INTEGER,
				arrayDiskLargestContiguousFreeSpaceInMB
					INTEGER,
				arrayDiskLargestContiguousFreeSpaceInBytes
					INTEGER,
				arrayDiskTargetID
					INTEGER,
				arrayDiskLunID
					INTEGER,
				arrayDiskUsedSpaceInMB
					INTEGER,
				arrayDiskUsedSpaceInBytes
					INTEGER,
				arrayDiskFreeSpaceInMB
					INTEGER,
				arrayDiskFreeSpaceInBytes
					INTEGER,
				arrayDiskBusType
					INTEGER,
				arrayDiskSpareState
					INTEGER
			 }

		-- 1.3.6.1.4.1.674.10893.1.1.130.4.1.1
		arrayDiskNumber OBJECT-TYPE
			SYNTAX INTEGER (1..1000000000)
			ACCESS read-only
			STATUS mandatory
			DESCRIPTION
				"Instance number of this array disk entry."
			::= { arrayDiskEntry 1 }


		-- 1.3.6.1.4.1.674.10893.1.1.130.4.1.2
		arrayDiskName OBJECT-TYPE
			SYNTAX DisplayString
			ACCESS read-only
			STATUS mandatory
			DESCRIPTION
				"The name of the array disk as represented in Array Manager."
			::= { arrayDiskEntry 2 }


		-- 1.3.6.1.4.1.674.10893.1.1.130.4.1.3
		arrayDiskVendor OBJECT-TYPE
			SYNTAX DisplayString
			ACCESS read-only
			STATUS mandatory
			DESCRIPTION
				"The array disk's (re)seller's name."
			::= { arrayDiskEntry 3 }


		-- 1.3.6.1.4.1.674.10893.1.1.130.4.1.4
		arrayDiskState OBJECT-TYPE
			SYNTAX INTEGER
				{
				ready(1),
				failed(2),
				online(3),
				offline(4),
				degraded(6),
				recovering(7),
				removed(11),
				resynching(15),
				rebuild(24),
				noMedia(25),
				formatting(26),
				diagnostics(28),
				initializing(35)
				}
			ACCESS read-only
			STATUS mandatory
			DESCRIPTION
				"The current state of the array disk.
				Possible states:
				 0: Unknown
				 1: Ready - Available for use, but no RAID configuration has been assigned.
				 2: Failed - Not operational.
				 3: Online - Operational. RAID configuration has been assigned.
				 4: Offline - The drive is not available to the RAID controller.
				 6: Degraded - Refers to a fault-tolerant array/virtual disk that has a failed disk.
				 7: Recovering - Refers to state of recovering from bad blocks on disks.
				11: Removed - Indicates that array disk has been removed.
				15: Resynching - Indicates one of the following types of disk operations: Transform Type, Reconfiguration, and Check Consistency.
				24: Rebuild
				25: No Media - CD-ROM or removable disk has no media.
				26: Formatting - In the process of formatting.
				28: Diagnostics - Diagnostics are running.
				35: Initializing: Applies only to virtual disks on PERC, PERC 2/SC, and PERC 2/DC controllers.
				"
			::= { arrayDiskEntry 4 }


		-- 1.3.6.1.4.1.674.10893.1.1.130.4.1.5
		arrayDiskSeverity OBJECT-TYPE
			SYNTAX INTEGER
				{
				warning(1),
				error(2),
				failure(3)
				}
			ACCESS read-only
			STATUS mandatory
			DESCRIPTION
				"Severity of the array disk state.
				Possible values:
				0: OK
				1: Warning
				2: Error
				3: Failure"
			::= { arrayDiskEntry 5 }


		-- 1.3.6.1.4.1.674.10893.1.1.130.4.1.6
		arrayDiskProductID OBJECT-TYPE
			SYNTAX DisplayString
			ACCESS read-only
			STATUS mandatory
			DESCRIPTION
				"The model number of the array disk."
			::= { arrayDiskEntry 6 }


		-- 1.3.6.1.4.1.674.10893.1.1.130.4.1.7
		arrayDiskSerialNo OBJECT-TYPE
			SYNTAX DisplayString
			ACCESS read-only
			STATUS mandatory
			DESCRIPTION
				"The array disk's unique identification number from the manufacturer."
			::= { arrayDiskEntry 7 }


		-- 1.3.6.1.4.1.674.10893.1.1.130.4.1.8
		arrayDiskRevision OBJECT-TYPE
			SYNTAX DisplayString
			ACCESS read-only
			STATUS mandatory
			DESCRIPTION
				"The firmware version of the array disk."
			::= { arrayDiskEntry 8 }


		-- 1.3.6.1.4.1.674.10893.1.1.130.4.1.9
		arrayDiskEnclosureID OBJECT-TYPE
			SYNTAX DisplayString
			ACCESS read-only
			STATUS mandatory
			DESCRIPTION
				"The SCSI ID of the enclosure processor to which this array disk belongs."
			::= { arrayDiskEntry 9 }


		-- 1.3.6.1.4.1.674.10893.1.1.130.4.1.10
		arrayDiskChannel OBJECT-TYPE
			SYNTAX INTEGER
			ACCESS read-only
			STATUS mandatory
			DESCRIPTION
				"The bus to which this array disk is connected."
			::= { arrayDiskEntry 10 }


		-- 1.3.6.1.4.1.674.10893.1.1.130.4.1.11
		arrayDiskLengthInMB OBJECT-TYPE
			SYNTAX INTEGER
			ACCESS read-only
			STATUS mandatory
			DESCRIPTION
				"The size in megabytes of the array disk. If this size
				is 0, it is smaller than a megabyte."
			::= { arrayDiskEntry 11 }


		-- 1.3.6.1.4.1.674.10893.1.1.130.4.1.12
		arrayDiskLengthInBytes OBJECT-TYPE
			SYNTAX INTEGER
			ACCESS read-only
			STATUS mandatory
			DESCRIPTION
				"The size of the array disk in bytes that is less than
				a megabyte. This size plus the arrayDiskLengthInMB is
				the total size of the array disk."
			::= { arrayDiskEntry 12 }


		-- 1.3.6.1.4.1.674.10893.1.1.130.4.1.13
		arrayDiskLargestContiguousFreeSpaceInMB OBJECT-TYPE
			SYNTAX INTEGER
			ACCESS read-only
			STATUS mandatory
			DESCRIPTION
				"The size in megabytes of the largest contiguous free space
				on the array disk. If this size is 0, it is less than a
				megabyte."
			::= { arrayDiskEntry 13 }


		-- 1.3.6.1.4.1.674.10893.1.1.130.4.1.14
		arrayDiskLargestContiguousFreeSpaceInBytes OBJECT-TYPE
			SYNTAX INTEGER
			ACCESS read-only
			STATUS mandatory
			DESCRIPTION
				"The size of the largest contiguouis free space on this
				array disk in bytes that is less than a megabyte.
				This size plus the arrayDiskLargestContiguousFreeSpaceInMB
				is the total size of the largest contiguous free space on
				the array disk."
			::= { arrayDiskEntry 14 }


		-- 1.3.6.1.4.1.674.10893.1.1.130.4.1.15
		arrayDiskTargetID OBJECT-TYPE
			SYNTAX INTEGER (0..15)
			ACCESS read-only
			STATUS mandatory
			DESCRIPTION
				"The SCSI target ID which this array disk is assigned. "
			::= { arrayDiskEntry 15 }


		-- 1.3.6.1.4.1.674.10893.1.1.130.4.1.16
		arrayDiskLunID OBJECT-TYPE
			SYNTAX INTEGER
			ACCESS read-only
			STATUS mandatory
			DESCRIPTION
				"The array disk's logical unit number. "
			::= { arrayDiskEntry 16 }


		-- 1.3.6.1.4.1.674.10893.1.1.130.4.1.17
		arrayDiskUsedSpaceInMB OBJECT-TYPE
			SYNTAX INTEGER
			ACCESS read-only
			STATUS mandatory
			DESCRIPTION
				"The amount in megabytes of the used space on the array
				disk. If this size is 0, it is smaller than a megabyte."
			::= { arrayDiskEntry 17 }


		-- 1.3.6.1.4.1.674.10893.1.1.130.4.1.18
		arrayDiskUsedSpaceInBytes OBJECT-TYPE
			SYNTAX INTEGER
			ACCESS read-only
			STATUS mandatory
			DESCRIPTION
				"The size in bytes of the used space on the array disk
				that is smaller than a megabyte. This size plus the
				arrayDiskUsedSpaceInMB is the total amount of used space
				on the array disk."
			::= { arrayDiskEntry 18 }


		-- 1.3.6.1.4.1.674.10893.1.1.130.4.1.19
		arrayDiskFreeSpaceInMB OBJECT-TYPE
			SYNTAX INTEGER
			ACCESS read-only
			STATUS mandatory
			DESCRIPTION
				"The amount in megabytes of the free space on the array
				disk. If this size is 0, it is smaller than a megabyte."
			::= { arrayDiskEntry 19 }


		-- 1.3.6.1.4.1.674.10893.1.1.130.4.1.20
		arrayDiskFreeSpaceInBytes OBJECT-TYPE
			SYNTAX INTEGER
			ACCESS read-write
			STATUS mandatory
			DESCRIPTION
				"The size in bytes of the free space on the array disk
				that is smaller than a megabyte. This size plus the
				arrayDiskFreeSpaceInMB is the total amount of free space
				on the array disk."
			::= { arrayDiskEntry 20 }


		-- 1.3.6.1.4.1.674.10893.1.1.130.4.1.21
		arrayDiskBusType OBJECT-TYPE
			SYNTAX INTEGER
				{
				scsi(1),
				ide(2),
				fibre(3),
				ssa(4),
				usb(6)
				}
			ACCESS read-only
			STATUS mandatory
			DESCRIPTION
				"The bus type of the array disk.
				Possible values:
				1: SCSI
				2: IDE
				3: Fibre Channel
				4: SSA
				6: USB"
			::= { arrayDiskEntry 21 }


		-- 1.3.6.1.4.1.674.10893.1.1.130.4.1.22
		arrayDiskSpareState OBJECT-TYPE
			SYNTAX INTEGER
				{
				memberVD(1),
				memberDG(2),
				globalHotSpare(3),
				dedicatedHotSpare(4)
				}
			ACCESS read-write
			STATUS mandatory
			DESCRIPTION
				"The status of the array disk as a spare.
				Possible states:
				1: disk is a member of a virtual disk
				2: disk is a member of a disk group
				3: disk is a global hot spare
				4: disk is a dedicated hot spare"
			::= { arrayDiskEntry 22 }


		-- 1.3.6.1.4.1.674.10893.1.1.130.5
		arrayDiskEnclosureConnectionTable OBJECT-TYPE
			SYNTAX SEQUENCE OF ArrayDiskEnclosureConnectionEntry
			ACCESS not-accessible
			STATUS mandatory
			DESCRIPTION
				"A table of the connections between array disks,
				their enclosure, and their associated controller.
				For each object in the table, its object number
				corresponds to an instance number in the appropriate
				MIB table for that object where all of the object
				properties can be found."
			::= { physicalDevices 5 }


		-- 1.3.6.1.4.1.674.10893.1.1.130.5.1
		arrayDiskEnclosureConnectionEntry OBJECT-TYPE
			SYNTAX ArrayDiskEnclosureConnectionEntry
			ACCESS not-accessible
			STATUS mandatory
			INDEX { arrayDiskEnclosureConnectionNumber }
			::= { arrayDiskEnclosureConnectionTable 1 }


		ArrayDiskEnclosureConnectionEntry ::=
			SEQUENCE {
				arrayDiskEnclosureConnectionNumber
					INTEGER,
				arrayDiskEnclosureConnectionArrayDiskName
					DisplayString,
				arrayDiskEnclosureConnectionArrayDiskNumber
					INTEGER,
				arrayDiskEnclosureConnectionEnclosureName
					DisplayString,
				arrayDiskEnclosureConnectionEnclosureNumber
					INTEGER,
				arrayDiskEnclosureConnectionControllerName
					DisplayString,
				arrayDiskEnclosureConnectionControllerNumber
					INTEGER
			 }

		-- 1.3.6.1.4.1.674.10893.1.1.130.5.1.1
		arrayDiskEnclosureConnectionNumber OBJECT-TYPE
			SYNTAX INTEGER (1..1000000000)
			ACCESS read-only
			STATUS mandatory
			DESCRIPTION
				"Instance number of this array disk connection entry.
				This table shows the array disk to SCSI or Fibre Channel
				enclosure relationship."
			::= { arrayDiskEnclosureConnectionEntry 1 }


		-- 1.3.6.1.4.1.674.10893.1.1.130.5.1.2
		arrayDiskEnclosureConnectionArrayDiskName OBJECT-TYPE
			SYNTAX DisplayString
			ACCESS read-only
			STATUS mandatory
			DESCRIPTION
				"The name of the array disk in this connection
				as represented in Array Manager."
			::= { arrayDiskEnclosureConnectionEntry 2 }


		-- 1.3.6.1.4.1.674.10893.1.1.130.5.1.3
		arrayDiskEnclosureConnectionArrayDiskNumber OBJECT-TYPE
			SYNTAX INTEGER
			ACCESS read-only
			STATUS mandatory
			DESCRIPTION
				"The instance number of the array disk in the arrayDiskTable
				in this connection."
			::= { arrayDiskEnclosureConnectionEntry 3 }


		-- 1.3.6.1.4.1.674.10893.1.1.130.5.1.4
		arrayDiskEnclosureConnectionEnclosureName OBJECT-TYPE
			SYNTAX DisplayString
			ACCESS read-only
			STATUS mandatory
			DESCRIPTION
				"The name of the enclosure as represented in Array Manager
				to which this array disk belongs.
				"
			::= { arrayDiskEnclosureConnectionEntry 4 }


		-- 1.3.6.1.4.1.674.10893.1.1.130.5.1.5
		arrayDiskEnclosureConnectionEnclosureNumber OBJECT-TYPE
			SYNTAX INTEGER
			ACCESS read-only
			STATUS mandatory
			DESCRIPTION
				"The instance number in the enclosureTable of the enclosure
				to which this array disk belongs."
			::= { arrayDiskEnclosureConnectionEntry 5 }


		-- 1.3.6.1.4.1.674.10893.1.1.130.5.1.6
		arrayDiskEnclosureConnectionControllerName OBJECT-TYPE
			SYNTAX DisplayString
			ACCESS read-only
			STATUS mandatory
			DESCRIPTION
				"The name of the controller as represented in Array Manager
				to which this array disk is connected."
			::= { arrayDiskEnclosureConnectionEntry 6 }


		-- 1.3.6.1.4.1.674.10893.1.1.130.5.1.7
		arrayDiskEnclosureConnectionControllerNumber OBJECT-TYPE
			SYNTAX INTEGER
			ACCESS read-only
			STATUS mandatory
			DESCRIPTION
				"The instance number in the controllerTable of the controller
				to which this array disk is connected."
			::= { arrayDiskEnclosureConnectionEntry 7 }


		-- 1.3.6.1.4.1.674.10893.1.1.130.6
		arrayDiskChannelConnectionTable OBJECT-TYPE
			SYNTAX SEQUENCE OF ArrayDiskChannelConnectionEntry
			ACCESS not-accessible
			STATUS mandatory
			DESCRIPTION
				"A table of the connections between array
				disks, their channel, and their associated controller.
				For each object in the table, its object number
				corresponds to an instance number in the appropriate MIB
				table for that object where all of the object properties
				can be found."
			::= { physicalDevices 6 }


		-- 1.3.6.1.4.1.674.10893.1.1.130.6.1
		arrayDiskChannelConnectionEntry OBJECT-TYPE
			SYNTAX ArrayDiskChannelConnectionEntry
			ACCESS not-accessible
			STATUS mandatory
			INDEX { arrayDiskChannelConnectionNumber }
			::= { arrayDiskChannelConnectionTable 1 }


		ArrayDiskChannelConnectionEntry ::=
			SEQUENCE {
				arrayDiskChannelConnectionNumber
					INTEGER,
				arrayDiskChannelConnectionArrayDiskName
					DisplayString,
				arrayDiskChannelConnectionArrayDiskNumber
					INTEGER,
				arrayDiskChannelConnectionChannelName
					DisplayString,
				arrayDiskChannelConnectionChannelNumber
					INTEGER,
				arrayDiskChannelConnectionControllerName
					DisplayString,
				arrayDiskChannelConnectionControllerNumber
					INTEGER
			 }

		-- 1.3.6.1.4.1.674.10893.1.1.130.6.1.1
		arrayDiskChannelConnectionNumber OBJECT-TYPE
			SYNTAX INTEGER (1..1000000000)
			ACCESS read-only
			STATUS mandatory
			DESCRIPTION
				"Instance number of this array disk connection entry.
				This table shows the array disk to SCSI channel relationship.
				There is no enclosure service processor associated with these
				array disks."
			::= { arrayDiskChannelConnectionEntry 1 }


		-- 1.3.6.1.4.1.674.10893.1.1.130.6.1.2
		arrayDiskChannelConnectionArrayDiskName OBJECT-TYPE
			SYNTAX DisplayString
			ACCESS read-only
			STATUS mandatory
			DESCRIPTION
				"The name of the array disk in this connection
				as represented in Array Manager."
			::= { arrayDiskChannelConnectionEntry 2 }


		-- 1.3.6.1.4.1.674.10893.1.1.130.6.1.3
		arrayDiskChannelConnectionArrayDiskNumber OBJECT-TYPE
			SYNTAX INTEGER
			ACCESS read-only
			STATUS mandatory
			DESCRIPTION
				"The instance number of the array disk in the arrayDiskTable
				in this connection."
			::= { arrayDiskChannelConnectionEntry 3 }


		-- 1.3.6.1.4.1.674.10893.1.1.130.6.1.4
		arrayDiskChannelConnectionChannelName OBJECT-TYPE
			SYNTAX DisplayString
			ACCESS read-only
			STATUS mandatory
			DESCRIPTION
				"The name of the channel as represented in Array Manager
				to which is array disk is connected."
			::= { arrayDiskChannelConnectionEntry 4 }


		-- 1.3.6.1.4.1.674.10893.1.1.130.6.1.5
		arrayDiskChannelConnectionChannelNumber OBJECT-TYPE
			SYNTAX INTEGER
			ACCESS read-only
			STATUS mandatory
			DESCRIPTION
				"The instance number of the channel in the channelTable to
				which this array disk is connected."
			::= { arrayDiskChannelConnectionEntry 5 }


		-- 1.3.6.1.4.1.674.10893.1.1.130.6.1.6
		arrayDiskChannelConnectionControllerName OBJECT-TYPE
			SYNTAX DisplayString
			ACCESS read-only
			STATUS mandatory
			DESCRIPTION
				"The name of the controller as represented in Array Manager
				to which this array disk is connected."
			::= { arrayDiskChannelConnectionEntry 6 }


		-- 1.3.6.1.4.1.674.10893.1.1.130.6.1.7
		arrayDiskChannelConnectionControllerNumber OBJECT-TYPE
			SYNTAX INTEGER
			ACCESS read-only
			STATUS mandatory
			DESCRIPTION
				"The instance number in the controllerTable of the controller
				to which this array disk is connected."
			::= { arrayDiskChannelConnectionEntry 7 }


		-- 1.3.6.1.4.1.674.10893.1.1.130.7
		fanTable OBJECT-TYPE
			SYNTAX SEQUENCE OF FanEntry
			ACCESS not-accessible
			STATUS mandatory
			::= { physicalDevices 7 }


		-- 1.3.6.1.4.1.674.10893.1.1.130.7.1
		fanEntry OBJECT-TYPE
			SYNTAX FanEntry
			ACCESS not-accessible
			STATUS mandatory
			INDEX { fanNumber }
			::= { fanTable 1 }


		FanEntry ::=
			SEQUENCE {
				fanNumber
					INTEGER,
				fanName
					DisplayString,
				fanVendor
					DisplayString,
				fanState
					INTEGER,
				fanSeverity
					INTEGER,
				fanProbeUnit
					DisplayString,
				fanProbeMinWarning
					DisplayString,
				fanProbeMinCritical
					DisplayString,
				fanProbeMaxWarning
					DisplayString,
				fanProbeMaxCritical
					DisplayString,
				fanProbeCurrValue
					DisplayString,
				fan1PartNumber
					DisplayString,
				fan2PartNumber
					DisplayString
			 }

		-- 1.3.6.1.4.1.674.10893.1.1.130.7.1.1
		fanNumber OBJECT-TYPE
			SYNTAX INTEGER (1..1000000000)
			ACCESS read-only
			STATUS mandatory
			DESCRIPTION
				"Instance number of this fan entry."
			::= { fanEntry 1 }


		-- 1.3.6.1.4.1.674.10893.1.1.130.7.1.2
		fanName OBJECT-TYPE
			SYNTAX DisplayString
			ACCESS read-only
			STATUS mandatory
			DESCRIPTION
				"The fan's name as represented in Array Manager."
			::= { fanEntry 2 }


		-- 1.3.6.1.4.1.674.10893.1.1.130.7.1.3
		fanVendor OBJECT-TYPE
			SYNTAX DisplayString
			ACCESS read-only
			STATUS mandatory
			DESCRIPTION
				"The fan's (re)seller's name."
			::= { fanEntry 3 }


		-- 1.3.6.1.4.1.674.10893.1.1.130.7.1.4
		fanState OBJECT-TYPE
			SYNTAX INTEGER
				{
				ready(1),
				failed(2),
				degraded(6),
				removed(11),
				commLost(55)
				}
			ACCESS read-only
			STATUS mandatory
			DESCRIPTION
				"Current state of the fan.
				Possible states:
				0 : Unknown
				1 : Ready
				2 : Failed
				3 : Online
				4 : Offline
				6 : Degraded
				55: Communication Lost"
			::= { fanEntry 4 }


		-- 1.3.6.1.4.1.674.10893.1.1.130.7.1.5
		fanSeverity OBJECT-TYPE
			SYNTAX INTEGER
				{
				warning(1),
				error(2),
				failure(3)
				}
			ACCESS read-only
			STATUS mandatory
			DESCRIPTION
				"Seiousness of the fan state.
				Possible values:
				0: OK
				1: Warning
				2: Error
				3: Failure"
			::= { fanEntry 5 }


		-- 1.3.6.1.4.1.674.10893.1.1.130.7.1.6
		fanProbeUnit OBJECT-TYPE
			SYNTAX DisplayString
			ACCESS read-only
			STATUS mandatory
			::= { fanEntry 6 }


		-- 1.3.6.1.4.1.674.10893.1.1.130.7.1.7
		fanProbeMinWarning OBJECT-TYPE
			SYNTAX DisplayString
			ACCESS read-only
			STATUS mandatory
			DESCRIPTION
				"The minimum value that will force the fan into a warning state."
			::= { fanEntry 7 }


		-- 1.3.6.1.4.1.674.10893.1.1.130.7.1.8
		fanProbeMinCritical OBJECT-TYPE
			SYNTAX DisplayString
			ACCESS read-only
			STATUS mandatory
			DESCRIPTION
				"The minimum value that will force the fan into an error state."
			::= { fanEntry 8 }


		-- 1.3.6.1.4.1.674.10893.1.1.130.7.1.9
		fanProbeMaxWarning OBJECT-TYPE
			SYNTAX DisplayString
			ACCESS read-only
			STATUS mandatory
			DESCRIPTION
				"The maximum value that will force the fan into a warning state."
			::= { fanEntry 9 }


		-- 1.3.6.1.4.1.674.10893.1.1.130.7.1.10
		fanProbeMaxCritical OBJECT-TYPE
			SYNTAX DisplayString
			ACCESS read-only
			STATUS mandatory
			DESCRIPTION
				"The maximum value that will force the fan into an error state."
			::= { fanEntry 10 }


		-- 1.3.6.1.4.1.674.10893.1.1.130.7.1.11
		fanProbeCurrValue OBJECT-TYPE
			SYNTAX DisplayString
			ACCESS read-only
			STATUS mandatory
			DESCRIPTION
				"The current speed of the fan.
				"
			::= { fanEntry 11 }


		-- 1.3.6.1.4.1.674.10893.1.1.130.7.1.12
		fan1PartNumber OBJECT-TYPE
			SYNTAX DisplayString
			ACCESS read-only
			STATUS mandatory
			DESCRIPTION
				"The part number of the fan in the enclosure."
			::= { fanEntry 12 }


		-- 1.3.6.1.4.1.674.10893.1.1.130.7.1.13
		fan2PartNumber OBJECT-TYPE
			SYNTAX DisplayString
			ACCESS read-only
			STATUS mandatory
			DESCRIPTION
				"This entry is obsolete."
			::= { fanEntry 13 }


		-- 1.3.6.1.4.1.674.10893.1.1.130.8
		fanConnectionTable OBJECT-TYPE
			SYNTAX SEQUENCE OF FanConnectionEntry
			ACCESS not-accessible
			STATUS mandatory
			DESCRIPTION
				"A table of the connections between each fan on
				the managed node and its enclosure. Each enclosure
				number in the table corresponds to that enclosure instance
				in the Enclosure Table."
			::= { physicalDevices 8 }


		-- 1.3.6.1.4.1.674.10893.1.1.130.8.1
		fanConnectionEntry OBJECT-TYPE
			SYNTAX FanConnectionEntry
			ACCESS not-accessible
			STATUS mandatory
			INDEX { fanConnectionNumber }
			::= { fanConnectionTable 1 }


		FanConnectionEntry ::=
			SEQUENCE {
				fanConnectionNumber
					INTEGER,
				fanConnectionFanName
					DisplayString,
				fanConnectionFanNumber
					INTEGER,
				fanConnectionEnclosureName
					DisplayString,
				fanConnectionEnclosureNumber
					INTEGER
			 }

		-- 1.3.6.1.4.1.674.10893.1.1.130.8.1.1
		fanConnectionNumber OBJECT-TYPE
			SYNTAX INTEGER (1..255)
			ACCESS read-only
			STATUS mandatory
			DESCRIPTION
				"Instance number of this fan connection entry."
			::= { fanConnectionEntry 1 }


		-- 1.3.6.1.4.1.674.10893.1.1.130.8.1.2
		fanConnectionFanName OBJECT-TYPE
			SYNTAX DisplayString
			ACCESS read-only
			STATUS mandatory
			DESCRIPTION
				"The name of the fan in this connection
				as represented in Array Manager."
			::= { fanConnectionEntry 2 }


		-- 1.3.6.1.4.1.674.10893.1.1.130.8.1.3
		fanConnectionFanNumber OBJECT-TYPE
			SYNTAX INTEGER
			ACCESS read-only
			STATUS mandatory
			DESCRIPTION
				"The instance number of the fan in the fanTable in this
				connection."
			::= { fanConnectionEntry 3 }


		-- 1.3.6.1.4.1.674.10893.1.1.130.8.1.4
		fanConnectionEnclosureName OBJECT-TYPE
			SYNTAX DisplayString
			ACCESS read-only
			STATUS mandatory
			DESCRIPTION
				"The name of the enclosure as represented in Array Manager
				to which this fan belongs."
			::= { fanConnectionEntry 4 }


		-- 1.3.6.1.4.1.674.10893.1.1.130.8.1.5
		fanConnectionEnclosureNumber OBJECT-TYPE
			SYNTAX INTEGER
			ACCESS read-only
			STATUS mandatory
			DESCRIPTION
				"The instance number of the enclosure in the enclosureTable
				to which this fan belongs."
			::= { fanConnectionEntry 5 }


		-- 1.3.6.1.4.1.674.10893.1.1.130.9
		powersupplyTable OBJECT-TYPE
			SYNTAX SEQUENCE OF PowersupplyEntry
			ACCESS not-accessible
			STATUS mandatory
			::= { physicalDevices 9 }


		-- 1.3.6.1.4.1.674.10893.1.1.130.9.1
		powersupplyEntry OBJECT-TYPE
			SYNTAX PowersupplyEntry
			ACCESS not-accessible
			STATUS mandatory
			INDEX { powersupplyNumber }
			::= { powersupplyTable 1 }


		PowersupplyEntry ::=
			SEQUENCE {
				powersupplyNumber
					INTEGER,
				powersupplyName
					DisplayString,
				powersupplyVendor
					DisplayString,
				powersupplyState
					INTEGER,
				powersupplySeverity
					INTEGER,
				powersupply1PartNumber
					DisplayString,
				powersupply2PartNumber
					DisplayString
			 }

		-- 1.3.6.1.4.1.674.10893.1.1.130.9.1.1
		powersupplyNumber OBJECT-TYPE
			SYNTAX INTEGER (1..255)
			ACCESS read-only
			STATUS mandatory
			DESCRIPTION
				"Instance number of this powersupply entry."
			::= { powersupplyEntry 1 }


		-- 1.3.6.1.4.1.674.10893.1.1.130.9.1.2
		powersupplyName OBJECT-TYPE
			SYNTAX DisplayString
			ACCESS read-only
			STATUS mandatory
			DESCRIPTION
				"The power supply's name as represented in Array Manager."
			::= { powersupplyEntry 2 }


		-- 1.3.6.1.4.1.674.10893.1.1.130.9.1.3
		powersupplyVendor OBJECT-TYPE
			SYNTAX DisplayString
			ACCESS read-only
			STATUS mandatory
			DESCRIPTION
				"The power supply's (re)seller's name."
			::= { powersupplyEntry 3 }


		-- 1.3.6.1.4.1.674.10893.1.1.130.9.1.4
		powersupplyState OBJECT-TYPE
			SYNTAX INTEGER
				{
				ready(1),
				failed(2),
				commLost(55)
				}
			ACCESS read-only
			STATUS mandatory
			DESCRIPTION
				"Current state of the power supply.
				Possible states:
				0 : Unknown
				1 : Ready
				2 : Failed
				55: Communication Lost"
			::= { powersupplyEntry 4 }


		-- 1.3.6.1.4.1.674.10893.1.1.130.9.1.5
		powersupplySeverity OBJECT-TYPE
			SYNTAX INTEGER
				{
				warning(1),
				error(2),
				failure(3)
				}
			ACCESS read-only
			STATUS mandatory
			DESCRIPTION
				"Seriousness of the power supply state.
				Possible values:
				0: OK
				1: Warning
				2: Error
				3: Failure"
			::= { powersupplyEntry 5 }


		-- 1.3.6.1.4.1.674.10893.1.1.130.9.1.6
		powersupply1PartNumber OBJECT-TYPE
			SYNTAX DisplayString
			ACCESS read-only
			STATUS mandatory
			DESCRIPTION
				"The part number of the power supply of the enclosure."
			::= { powersupplyEntry 6 }


		-- 1.3.6.1.4.1.674.10893.1.1.130.9.1.7
		powersupply2PartNumber OBJECT-TYPE
			SYNTAX DisplayString
			ACCESS read-only
			STATUS mandatory
			DESCRIPTION
				"This entry is obsolete."
			::= { powersupplyEntry 7 }


		-- 1.3.6.1.4.1.674.10893.1.1.130.10
		powersupplyConnectionTable OBJECT-TYPE
			SYNTAX SEQUENCE OF PowersupplyConnectionEntry
			ACCESS not-accessible
			STATUS mandatory
			DESCRIPTION
				"A table of the connections between each power
				supply on the managed node and its enclosure. Each
				enclosure number in the table corresponds to that
				enclosure instance in the Enclosure Table."
			::= { physicalDevices 10 }


		-- 1.3.6.1.4.1.674.10893.1.1.130.10.1
		powersupplyConnectionEntry OBJECT-TYPE
			SYNTAX PowersupplyConnectionEntry
			ACCESS not-accessible
			STATUS mandatory
			INDEX { powersupplyConnectionNumber }
			::= { powersupplyConnectionTable 1 }


		PowersupplyConnectionEntry ::=
			SEQUENCE {
				powersupplyConnectionNumber
					INTEGER,
				powersupplyConnectionPowersupplyName
					DisplayString,
				powersupplyConnectionPowersupplyNumber
					INTEGER,
				powersupplyConnectionEnclosureName
					DisplayString,
				powersupplyConnectionEnclosureNumber
					INTEGER
			 }

		-- 1.3.6.1.4.1.674.10893.1.1.130.10.1.1
		powersupplyConnectionNumber OBJECT-TYPE
			SYNTAX INTEGER (1..255)
			ACCESS read-only
			STATUS mandatory
			DESCRIPTION
				"Instance number of this powersupply connection entry."
			::= { powersupplyConnectionEntry 1 }


		-- 1.3.6.1.4.1.674.10893.1.1.130.10.1.2
		powersupplyConnectionPowersupplyName OBJECT-TYPE
			SYNTAX DisplayString
			ACCESS read-only
			STATUS mandatory
			DESCRIPTION
				"The name of the power supply in this connection
				as represented in Array Manager."
			::= { powersupplyConnectionEntry 2 }


		-- 1.3.6.1.4.1.674.10893.1.1.130.10.1.3
		powersupplyConnectionPowersupplyNumber OBJECT-TYPE
			SYNTAX INTEGER
			ACCESS read-only
			STATUS mandatory
			DESCRIPTION
				"This instance number in the powersupplyTable
				of the power supply in this connection."
			::= { powersupplyConnectionEntry 3 }


		-- 1.3.6.1.4.1.674.10893.1.1.130.10.1.4
		powersupplyConnectionEnclosureName OBJECT-TYPE
			SYNTAX DisplayString
			ACCESS read-only
			STATUS mandatory
			DESCRIPTION
				"The name of the enclosure to which this power supply is
				connected as represented in Array Manager."
			::= { powersupplyConnectionEntry 4 }


		-- 1.3.6.1.4.1.674.10893.1.1.130.10.1.5
		powersupplyConnectionEnclosureNumber OBJECT-TYPE
			SYNTAX INTEGER
			ACCESS read-write
			STATUS mandatory
			DESCRIPTION
				"The instance number of the enclosure in the enclosureTable
				to which this power supply is connected."
			::= { powersupplyConnectionEntry 5 }


		-- 1.3.6.1.4.1.674.10893.1.1.130.11
		temperatureTable OBJECT-TYPE
			SYNTAX SEQUENCE OF TemperatureEntry
			ACCESS not-accessible
			STATUS mandatory
			::= { physicalDevices 11 }


		-- 1.3.6.1.4.1.674.10893.1.1.130.11.1
		temperatureEntry OBJECT-TYPE
			SYNTAX TemperatureEntry
			ACCESS not-accessible
			STATUS mandatory
			INDEX { temperatureNumber }
			::= { temperatureTable 1 }


		TemperatureEntry ::=
			SEQUENCE {
				temperatureNumber
					INTEGER,
				temperatureName
					DisplayString,
				temperatureVendor
					DisplayString,
				temperatureState
					INTEGER,
				temperatureSeverity
					INTEGER,
				temperatureProbeUnit
					DisplayString,
				temperatureProbeMinWarning
					INTEGER,
				temperatureProbeMinCritical
					INTEGER,
				temperatureProbeMaxWarning
					INTEGER,
				temperatureProbeMaxCritical
					INTEGER,
				temperatureProbeCurValue
					INTEGER
			 }

		-- 1.3.6.1.4.1.674.10893.1.1.130.11.1.1
		temperatureNumber OBJECT-TYPE
			SYNTAX INTEGER (1..255)
			ACCESS read-only
			STATUS mandatory
			DESCRIPTION
				"Instance number of this temperature probe entry."
			::= { temperatureEntry 1 }


		-- 1.3.6.1.4.1.674.10893.1.1.130.11.1.2
		temperatureName OBJECT-TYPE
			SYNTAX DisplayString
			ACCESS read-only
			STATUS mandatory
			DESCRIPTION
				"Name of this temperature probe as represented in Array Manager."
			::= { temperatureEntry 2 }


		-- 1.3.6.1.4.1.674.10893.1.1.130.11.1.3
		temperatureVendor OBJECT-TYPE
			SYNTAX DisplayString
			ACCESS read-only
			STATUS mandatory
			DESCRIPTION
				"Temperature probe's (re)seller's name."
			::= { temperatureEntry 3 }


		-- 1.3.6.1.4.1.674.10893.1.1.130.11.1.4
		temperatureState OBJECT-TYPE
			SYNTAX INTEGER
				{
				ready(1),
				failed(2),
				offline(4),
				degraded(6),
				commLost(55)
				}
			ACCESS read-only
			STATUS mandatory
			DESCRIPTION
				"Current state of this temperature probe.
				Possible states:
				0 : Unknown
				1 : Ready
				2 : Failed
				4 : Offline
				6 : Degraded
				55: Communication Lost"
			::= { temperatureEntry 4 }


		-- 1.3.6.1.4.1.674.10893.1.1.130.11.1.5
		temperatureSeverity OBJECT-TYPE
			SYNTAX INTEGER
				{
				warning(1),
				error(2),
				failure(3)
				}
			ACCESS read-only
			STATUS mandatory
			DESCRIPTION
				"Seriousness of the temperature probe state.
				Possible values:
				0: OK
				1: Warning
				2: Error
				3: Failure"
			::= { temperatureEntry 5 }


		-- 1.3.6.1.4.1.674.10893.1.1.130.11.1.6
		temperatureProbeUnit OBJECT-TYPE
			SYNTAX DisplayString
			ACCESS read-only
			STATUS mandatory
			DESCRIPTION
				"The units that will be used to display temperatures for this
				temperature probe."
			::= { temperatureEntry 6 }


		-- 1.3.6.1.4.1.674.10893.1.1.130.11.1.7
		temperatureProbeMinWarning OBJECT-TYPE
			SYNTAX INTEGER
			ACCESS read-only
			STATUS mandatory
			DESCRIPTION
				"The minimum temperature that will force the probe into
				a warning state."
			::= { temperatureEntry 7 }


		-- 1.3.6.1.4.1.674.10893.1.1.130.11.1.8
		temperatureProbeMinCritical OBJECT-TYPE
			SYNTAX INTEGER
			ACCESS read-only
			STATUS mandatory
			DESCRIPTION
				"The minimum temperature that will force the probe into
				an error state."
			::= { temperatureEntry 8 }


		-- 1.3.6.1.4.1.674.10893.1.1.130.11.1.9
		temperatureProbeMaxWarning OBJECT-TYPE
			SYNTAX INTEGER
			ACCESS read-only
			STATUS mandatory
			DESCRIPTION
				"The maximum temperature that will force the probe into
				a warning state."
			::= { temperatureEntry 9 }


		-- 1.3.6.1.4.1.674.10893.1.1.130.11.1.10
		temperatureProbeMaxCritical OBJECT-TYPE
			SYNTAX INTEGER
			ACCESS read-only
			STATUS mandatory
			DESCRIPTION
				"The maximum temperature that will force the probe into
				an error state."
			::= { temperatureEntry 10 }


		-- 1.3.6.1.4.1.674.10893.1.1.130.11.1.11
		temperatureProbeCurValue OBJECT-TYPE
			SYNTAX INTEGER
			ACCESS read-only
			STATUS mandatory
			DESCRIPTION
				"The current temperature of this probe."
			::= { temperatureEntry 11 }


		-- 1.3.6.1.4.1.674.10893.1.1.130.12
		temperatureConnectionTable OBJECT-TYPE
			SYNTAX SEQUENCE OF TemperatureConnectionEntry
			ACCESS not-accessible
			STATUS mandatory
			DESCRIPTION
				"A table of the connections between each
				temperature probe on the managed node and its enclosure.
				Each enclosure number in the table corresponds to that
				enclosure instance in the Enclosure Table."
			::= { physicalDevices 12 }


		-- 1.3.6.1.4.1.674.10893.1.1.130.12.1
		temperatureConnectionEntry OBJECT-TYPE
			SYNTAX TemperatureConnectionEntry
			ACCESS not-accessible
			STATUS mandatory
			INDEX { temperatureConnectionNumber }
			::= { temperatureConnectionTable 1 }


		TemperatureConnectionEntry ::=
			SEQUENCE {
				temperatureConnectionNumber
					INTEGER,
				temperatureConnectionTemperatureName
					DisplayString,
				temperatureConnectionTemperatureNumber
					INTEGER,
				temperatureConnectionEnclosureName
					DisplayString,
				temperatureConnectionEnclosureNumber
					INTEGER
			 }

		-- 1.3.6.1.4.1.674.10893.1.1.130.12.1.1
		temperatureConnectionNumber OBJECT-TYPE
			SYNTAX INTEGER (1..255)
			ACCESS read-only
			STATUS mandatory
			DESCRIPTION
				"Instance number of this temperature probe connection entry."
			::= { temperatureConnectionEntry 1 }


		-- 1.3.6.1.4.1.674.10893.1.1.130.12.1.2
		temperatureConnectionTemperatureName OBJECT-TYPE
			SYNTAX DisplayString
			ACCESS read-only
			STATUS mandatory
			DESCRIPTION
				"The name of the temperature probe in this connection as
				represented in Array Manager."
			::= { temperatureConnectionEntry 2 }


		-- 1.3.6.1.4.1.674.10893.1.1.130.12.1.3
		temperatureConnectionTemperatureNumber OBJECT-TYPE
			SYNTAX INTEGER
			ACCESS read-only
			STATUS mandatory
			DESCRIPTION
				"The instance number in the temperatureTable
				of the temperature probe in this connection."
			::= { temperatureConnectionEntry 3 }


		-- 1.3.6.1.4.1.674.10893.1.1.130.12.1.4
		temperatureConnectionEnclosureName OBJECT-TYPE
			SYNTAX DisplayString
			ACCESS read-only
			STATUS mandatory
			DESCRIPTION
				"The name of the enclosure as represented in Array Manager
				to which this temperature probe belongs."
			::= { temperatureConnectionEntry 4 }


		-- 1.3.6.1.4.1.674.10893.1.1.130.12.1.5
		temperatureConnectionEnclosureNumber OBJECT-TYPE
			SYNTAX INTEGER
			ACCESS read-only
			STATUS mandatory
			DESCRIPTION
				"The instance number of the enclosure in the enclosureTable
				to which this temperature probe belongs.
				"
			::= { temperatureConnectionEntry 5 }


		-- 1.3.6.1.4.1.674.10893.1.1.130.13
		enclosureManagementModuleTable OBJECT-TYPE
			SYNTAX SEQUENCE OF EnclosureManagementModuleEntry
			ACCESS not-accessible
			STATUS mandatory
			DESCRIPTION
				"A table of managed Enclosure Memory Modules. The number of
				entries is related to number of Enclosure Memory Modules
				discovered in the system. The maximum number of entries
				is implementation dependent."
			::= { physicalDevices 13 }


		-- 1.3.6.1.4.1.674.10893.1.1.130.13.1
		enclosureManagementModuleEntry OBJECT-TYPE
			SYNTAX EnclosureManagementModuleEntry
			ACCESS not-accessible
			STATUS mandatory
			INDEX { enclosureManagementModuleNumber }
			::= { enclosureManagementModuleTable 1 }


		EnclosureManagementModuleEntry ::=
			SEQUENCE {
				enclosureManagementModuleNumber
					INTEGER,
				enclosureManagementModuleName
					DisplayString,
				enclosureManagementModuleVendor
					DisplayString,
				enclosureManagementModuleState
					INTEGER,
				enclosureManagementModuleSeverity
					INTEGER,
				enclosureManagementModulePartNumber
					DisplayString,
				enclosureManagementModuleType
					INTEGER,
				enclosureManagementModuleFWVersion
					DisplayString,
				enclosureManagementModuleMaxSpeed
					DisplayString
			 }

		-- 1.3.6.1.4.1.674.10893.1.1.130.13.1.1
		enclosureManagementModuleNumber OBJECT-TYPE
			SYNTAX INTEGER (1..255)
			ACCESS read-only
			STATUS mandatory
			DESCRIPTION
				"Instance number of this enclosure memory module entry."
			::= { enclosureManagementModuleEntry 1 }


		-- 1.3.6.1.4.1.674.10893.1.1.130.13.1.2
		enclosureManagementModuleName OBJECT-TYPE
			SYNTAX DisplayString
			ACCESS read-only
			STATUS mandatory
			DESCRIPTION
				"Name of this enclosure memory module as represented in
				Array Manager."
			::= { enclosureManagementModuleEntry 2 }


		-- 1.3.6.1.4.1.674.10893.1.1.130.13.1.3
		enclosureManagementModuleVendor OBJECT-TYPE
			SYNTAX DisplayString
			ACCESS read-only
			STATUS mandatory
			DESCRIPTION
				"The management module's (re)seller's name."
			::= { enclosureManagementModuleEntry 3 }


		-- 1.3.6.1.4.1.674.10893.1.1.130.13.1.4
		enclosureManagementModuleState OBJECT-TYPE
			SYNTAX INTEGER
				{
				ready(1),
				failed(2),
				online(3),
				offline(4),
				degraded(6),
				commLost(55)
				}
			ACCESS read-only
			STATUS mandatory
			DESCRIPTION
				"The state of the enclosure management module.
				Possible states:
				0 : Unknown
				1 : Ready
				2 : Failed
				3 : Online
				4 : Offline
				6 : Degraded
				55: Communication Lost"
			::= { enclosureManagementModuleEntry 4 }


		-- 1.3.6.1.4.1.674.10893.1.1.130.13.1.5
		enclosureManagementModuleSeverity OBJECT-TYPE
			SYNTAX INTEGER
			ACCESS read-only
			STATUS mandatory
			DESCRIPTION
				"Seriousness of the enclosure management module state.
				Possible values:
				0: OK
				1: Warning
				2: Error
				3: Failure"
			::= { enclosureManagementModuleEntry 5 }


		-- 1.3.6.1.4.1.674.10893.1.1.130.13.1.6
		enclosureManagementModulePartNumber OBJECT-TYPE
			SYNTAX DisplayString
			ACCESS read-only
			STATUS mandatory
			DESCRIPTION
				"The part number of the enclosure memory module."
			::= { enclosureManagementModuleEntry 6 }


		-- 1.3.6.1.4.1.674.10893.1.1.130.13.1.7
		enclosureManagementModuleType OBJECT-TYPE
			SYNTAX INTEGER
				{
				eMM(1),
				terminationCard(2)
				}
			ACCESS read-only
			STATUS mandatory
			DESCRIPTION
				"The type of the enclosure management module.
				Possible values:
				0: Unknown
				1: EMM
				2: Termination Card"
			::= { enclosureManagementModuleEntry 7 }


		-- 1.3.6.1.4.1.674.10893.1.1.130.13.1.8
		enclosureManagementModuleFWVersion OBJECT-TYPE
			SYNTAX DisplayString
			ACCESS read-only
			STATUS mandatory
			DESCRIPTION
				"Firmware version of the enclosure memory module."
			::= { enclosureManagementModuleEntry 8 }


		-- 1.3.6.1.4.1.674.10893.1.1.130.13.1.9
		enclosureManagementModuleMaxSpeed OBJECT-TYPE
			SYNTAX DisplayString
			ACCESS read-only
			STATUS mandatory
			DESCRIPTION
				"The maximum bus speed of the enclosure management module."
			::= { enclosureManagementModuleEntry 9 }


		-- 1.3.6.1.4.1.674.10893.1.1.130.14
		enclosureManagementModuleConnectionTable OBJECT-TYPE
			SYNTAX SEQUENCE OF EnclosureManagementModuleConnectionEntry
			ACCESS not-accessible
			STATUS mandatory
			DESCRIPTION
				"A table of the connections between each enclosure management module
				on the managed node and its enclosure. Each enclosure
				number in the table corresponds to that enclosure instance
				in the Enclosure Table."
			::= { physicalDevices 14 }


		-- 1.3.6.1.4.1.674.10893.1.1.130.14.1
		enclosureManagementModuleConnectionEntry OBJECT-TYPE
			SYNTAX EnclosureManagementModuleConnectionEntry
			ACCESS not-accessible
			STATUS mandatory
			INDEX { enclosureManagementModuleConnectionNumber }
			::= { enclosureManagementModuleConnectionTable 1 }


		EnclosureManagementModuleConnectionEntry ::=
			SEQUENCE {
				enclosureManagementModuleConnectionNumber
					INTEGER,
				enclosureManagementModuleConnectionEMMName
					DisplayString,
				enclosureManagementModuleConnectionEMMNumber
					INTEGER,
				enclosureManagementModuleConnectionEnclosureName
					DisplayString,
				enclosureManagementModuleConnectionEnclosureNumber
					INTEGER
			 }

		-- 1.3.6.1.4.1.674.10893.1.1.130.14.1.1
		enclosureManagementModuleConnectionNumber OBJECT-TYPE
			SYNTAX INTEGER (1..255)
			ACCESS read-only
			STATUS mandatory
			DESCRIPTION
				"Instance number of this enclosure management module
				connection entry."
			::= { enclosureManagementModuleConnectionEntry 1 }


		-- 1.3.6.1.4.1.674.10893.1.1.130.14.1.2
		enclosureManagementModuleConnectionEMMName OBJECT-TYPE
			SYNTAX DisplayString
			ACCESS read-only
			STATUS mandatory
			DESCRIPTION
				"The name of the enclosure management module in this
				connection as represented in Array Manager."
			::= { enclosureManagementModuleConnectionEntry 2 }


		-- 1.3.6.1.4.1.674.10893.1.1.130.14.1.3
		enclosureManagementModuleConnectionEMMNumber OBJECT-TYPE
			SYNTAX INTEGER
			ACCESS read-only
			STATUS mandatory
			DESCRIPTION
				"The instance number of the enclosure management module in
				the enclosureManagementModuleTable in this connection."
			::= { enclosureManagementModuleConnectionEntry 3 }


		-- 1.3.6.1.4.1.674.10893.1.1.130.14.1.4
		enclosureManagementModuleConnectionEnclosureName OBJECT-TYPE
			SYNTAX DisplayString
			ACCESS read-only
			STATUS mandatory
			DESCRIPTION
				"The name of the enclosure as represented in Array Manager
				to which this enclosure management module belongs."
			::= { enclosureManagementModuleConnectionEntry 4 }


		-- 1.3.6.1.4.1.674.10893.1.1.130.14.1.5
		enclosureManagementModuleConnectionEnclosureNumber OBJECT-TYPE
			SYNTAX INTEGER
			ACCESS read-only
			STATUS mandatory
			DESCRIPTION
				"The instance number of the enclosure in the enclosureTable
				to which this enclosure management module belongs"
			::= { enclosureManagementModuleConnectionEntry 5 }


-- This group and all of its associated tables and objects are not
-- supported on Microsoft Windows .NET 64-bit on a PE7150.
		-- 1.3.6.1.4.1.674.10893.1.1.140
		logicalDevices OBJECT IDENTIFIER ::= { arrayManager 140 }


		-- 1.3.6.1.4.1.674.10893.1.1.140.1
		virtualDiskTable OBJECT-TYPE
			SYNTAX SEQUENCE OF VirtualDiskEntry
			ACCESS not-accessible
			STATUS mandatory
			DESCRIPTION
				"A table of managed Virtual Disks. The number of entries is related
				to number of Virtual Disks discovered in the system.
				The maximum number of entries is implementation dependent."
			::= { logicalDevices 1 }


		-- 1.3.6.1.4.1.674.10893.1.1.140.1.1
		virtualDiskEntry OBJECT-TYPE
			SYNTAX VirtualDiskEntry
			ACCESS not-accessible
			STATUS mandatory
			DESCRIPTION
				"An entry in the Virtual Disk table. A row in this table cannot be
				created or deleted by SNMP operations on columns of the table."
			INDEX { virtualDiskNumber }
			::= { virtualDiskTable 1 }


		VirtualDiskEntry ::=
			SEQUENCE {
				virtualDiskNumber
					INTEGER,
				virtualDiskName
					DisplayString,
				virtualDiskDeviceName
					DisplayString,
				virtualDiskState
					INTEGER,
				virtualDiskSeverity
					INTEGER,
				virtualDiskLengthInMB
					INTEGER,
				virtualDiskLengthInBytes
					INTEGER,
				virtualDiskFreeSpaceInMB
					INTEGER,
				virtualDiskFreeSpaceInBytes
					INTEGER,
				virtualDiskWritePolicy
					INTEGER,
				virtualDiskReadPolicy
					INTEGER,
				virtualDiskCachePolicy
					INTEGER,
				virtualDiskLayout
					INTEGER,
				virtualDiskCurStripeSizeInMB
					INTEGER,
				virtualDiskCurStripeSizeInBytes
					INTEGER,
				virtualDiskChannel
					INTEGER,
				virtualDiskTargetID
					INTEGER,
				virtualDiskLunID
					INTEGER
			 }

		-- 1.3.6.1.4.1.674.10893.1.1.140.1.1.1
		virtualDiskNumber OBJECT-TYPE
			SYNTAX INTEGER (1..100000000)
			ACCESS read-only
			STATUS mandatory
			DESCRIPTION
				"Instance number of this virtual disk entry."
			::= { virtualDiskEntry 1 }


		-- 1.3.6.1.4.1.674.10893.1.1.140.1.1.2
		virtualDiskName OBJECT-TYPE
			SYNTAX DisplayString
			ACCESS read-only
			STATUS mandatory
			DESCRIPTION
				"The virtual disk's label generated by the provider or entered
				by the user."
			::= { virtualDiskEntry 2 }


		-- 1.3.6.1.4.1.674.10893.1.1.140.1.1.3
		virtualDiskDeviceName OBJECT-TYPE
			SYNTAX DisplayString
			ACCESS read-only
			STATUS mandatory
			DESCRIPTION
				"Device name used by this virtual disk's member disks."
			::= { virtualDiskEntry 3 }


		-- 1.3.6.1.4.1.674.10893.1.1.140.1.1.4
		virtualDiskState OBJECT-TYPE
			SYNTAX INTEGER
				{
				ready(1),
				failed(2),
				online(3),
				offline(4),
				degraded(6),
				verifying(7),
				resynching(15),
				failedRedundancy(18),
				rebuilding(24),
				formatting(26),
				initializing(35)
				}
			ACCESS read-only
			STATUS mandatory
			DESCRIPTION
				"The current state of this virtual disk.
				Possible states:
				 0: Unknown
				 1: Ready - The disk is accessible and has no known problems.
				 2: Failed - Access has been lost to the data or is about to be lost.
				 3: Online
				 4: Offline - The disk is not accessible. The disk may be corrupted or intermittently unavailable.
				 6: Degraded - The data on the virtual disk is no longer fault tolerant because one of the underlying disks is not online.
				15: Resynching
				24: Rebuilding
				26: Formatting
				35: Initializing"
			::= { virtualDiskEntry 4 }


		-- 1.3.6.1.4.1.674.10893.1.1.140.1.1.5
		virtualDiskSeverity OBJECT-TYPE
			SYNTAX INTEGER
				{
				warning(1),
				error(2),
				failure(3)
				}
			ACCESS read-only
			STATUS mandatory
			DESCRIPTION
				"Seriousness of the virtual disk state.
				Possible values:
				0: OK
				1: Warning
				2: Error
				3: Failure"
			::= { virtualDiskEntry 5 }


		-- 1.3.6.1.4.1.674.10893.1.1.140.1.1.6
		virtualDiskLengthInMB OBJECT-TYPE
			SYNTAX INTEGER
			ACCESS read-only
			STATUS mandatory
			DESCRIPTION
				"The size of this virtual disk in megabytes. If this size
				is 0, it is smaller than a megabyte."
			::= { virtualDiskEntry 6 }


		-- 1.3.6.1.4.1.674.10893.1.1.140.1.1.7
		virtualDiskLengthInBytes OBJECT-TYPE
			SYNTAX INTEGER
			ACCESS read-only
			STATUS mandatory
			DESCRIPTION
				"The portion of the virtual disk in bytes that is smaller
				than a megabyte. This size plus the virtualDiskLengthInMB
				is the total size of the virtual disk."
			::= { virtualDiskEntry 7 }


		-- 1.3.6.1.4.1.674.10893.1.1.140.1.1.8
		virtualDiskFreeSpaceInMB OBJECT-TYPE
			SYNTAX INTEGER
			ACCESS read-only
			STATUS mandatory
			DESCRIPTION
				"Amount of free space in megabytes on virtual disk. If this
				size is 0, it is smaller than a megabyte."
			::= { virtualDiskEntry 8 }


		-- 1.3.6.1.4.1.674.10893.1.1.140.1.1.9
		virtualDiskFreeSpaceInBytes OBJECT-TYPE
			SYNTAX INTEGER
			ACCESS read-only
			STATUS mandatory
			DESCRIPTION
				"The portion of the free space on the virtual disk in bytes
				that is smaller than a megabyte. This size plus the
				virtualDiskFreeSpaceInMB is the total free space on the
				virtual disk."
			::= { virtualDiskEntry 9 }


		-- 1.3.6.1.4.1.674.10893.1.1.140.1.1.10
		virtualDiskWritePolicy OBJECT-TYPE
			SYNTAX INTEGER
				{
				enabled(1),
				disabled(2)
				}
			ACCESS read-only
			STATUS mandatory
			DESCRIPTION
				"Indicates whether the controller's write cache will be used
				when writing to a virtual disk.
				Possible values:
				1: Enabled - Write Back
				2: Disabled - Write Through"
			::= { virtualDiskEntry 10 }


		-- 1.3.6.1.4.1.674.10893.1.1.140.1.1.11
		virtualDiskReadPolicy OBJECT-TYPE
			SYNTAX INTEGER
				{
				enabled(1),
				disabled(2),
				adaptiveReadAhead(3)
				}
			ACCESS read-only
			STATUS mandatory
			DESCRIPTION
				"Indicates whether the controller's read cache will be used
				when reading from a virtual disk.
				Note: Virtual Disks on a PV660F do not have a read cache
				policy.
				Possible values:
				1: Enabled - Read Ahead
				2: Disabled - No Read Ahead
				3: Adaptive Read Ahead"
			::= { virtualDiskEntry 11 }


		-- 1.3.6.1.4.1.674.10893.1.1.140.1.1.12
		virtualDiskCachePolicy OBJECT-TYPE
			SYNTAX INTEGER
				{
				directIO(1),
				cachedIO(2)
				}
			ACCESS read-only
			STATUS mandatory
			DESCRIPTION
				"Indicates whether the controller's cache is used when
				reading from or writing to a virtual disk.
				Possible values:
				1: Direct I/O
				2: Cached I/O"
			::= { virtualDiskEntry 12 }


		-- 1.3.6.1.4.1.674.10893.1.1.140.1.1.13
		virtualDiskLayout OBJECT-TYPE
			SYNTAX INTEGER
				{
				concatenated(1),
				raid-0(2),
				raid-1(3),
				raid-2(4),
				raid-3(5),
				raid-4(6),
				raid-5(7),
				raid-6(8),
				raid-7(9),
				raid-10(10),
				raid-30(11),
				raid-50(12),
				addSpares(13),
				deleteLogical(14),
				transformLogical(15),
				raid-0-plus-1(18)
				}
			ACCESS read-only
			STATUS mandatory
			DESCRIPTION
				"The virtual disk's RAID type.
				Possible values:
				 1: Concatenated
				 2: Raid-0
				 3: Raid-1
				 4: Raid-2
				 5: Raid-3
				 6: Raid-4
				 7: Raid-5
				 8: Raid-6
				 9: Raid-7
				10: Raid-10
				11: Raid-30
				12: Raid-50
				13: Add Spares
				14: Delete Logical
				15: Transform Logical
				18: Raid-0-plus-1 (0+1)"
			::= { virtualDiskEntry 13 }


		-- 1.3.6.1.4.1.674.10893.1.1.140.1.1.14
		virtualDiskCurStripeSizeInMB OBJECT-TYPE
			SYNTAX INTEGER
			ACCESS read-only
			STATUS mandatory
			DESCRIPTION
				"The stripe size of this virtual disk in megabytes. If this
				size is 0, it is smaller than a megabyte.
				"
			::= { virtualDiskEntry 14 }


		-- 1.3.6.1.4.1.674.10893.1.1.140.1.1.15
		virtualDiskCurStripeSizeInBytes OBJECT-TYPE
			SYNTAX INTEGER
			ACCESS read-only
			STATUS mandatory
			DESCRIPTION
				"The portion of the stripe size in bytes that is smaller
				than a megabyte. This size plus the
				virtualDiskCurStripeSizeInMB is the total stripe size on
				the virtual disk."
			::= { virtualDiskEntry 15 }


		-- 1.3.6.1.4.1.674.10893.1.1.140.1.1.16
		virtualDiskChannel OBJECT-TYPE
			SYNTAX INTEGER
			ACCESS read-only
			STATUS mandatory
			DESCRIPTION
				"The virtual disk's channel number."
			::= { virtualDiskEntry 16 }


		-- 1.3.6.1.4.1.674.10893.1.1.140.1.1.17
		virtualDiskTargetID OBJECT-TYPE
			SYNTAX INTEGER
			ACCESS read-only
			STATUS mandatory
			DESCRIPTION
				"The virtual disk's target ID."
			::= { virtualDiskEntry 17 }


		-- 1.3.6.1.4.1.674.10893.1.1.140.1.1.18
		virtualDiskLunID OBJECT-TYPE
			SYNTAX INTEGER
			ACCESS read-only
			STATUS mandatory
			DESCRIPTION
				"The virtual disk's LUN ID."
			::= { virtualDiskEntry 18 }


		-- 1.3.6.1.4.1.674.10893.1.1.140.2
		diskTable OBJECT-TYPE
			SYNTAX SEQUENCE OF DiskEntry
			ACCESS not-accessible
			STATUS mandatory
			DESCRIPTION
				"A table of managed disks that are a member of a Virtual Disk.
				The number of entries is related to the number of online array
				disks discovered in the system. The maximum number of entries is
				implementation dependent."
			::= { logicalDevices 2 }


		-- 1.3.6.1.4.1.674.10893.1.1.140.2.1
		diskEntry OBJECT-TYPE
			SYNTAX DiskEntry
			ACCESS not-accessible
			STATUS mandatory
			DESCRIPTION
				"An entry in the Member Disk table. A row in this table cannot be
				created or deleted by SNMP operations on columns of the table."
			INDEX { diskNumber }
			::= { diskTable 1 }


		DiskEntry ::=
			SEQUENCE {
				diskNumber
					INTEGER,
				diskName
					DisplayString,
				diskVirtualDiskDeviceName
					DisplayString,
				diskState
					INTEGER,
				diskSeverity
					INTEGER,
				diskLdmDeviceType
					INTEGER,
				diskDgName
					DisplayString,
				diskLengthInMB
					INTEGER,
				diskLengthInBytes
					INTEGER,
				diskFreeSpaceInMB
					INTEGER,
				diskFreeSpaceInBytes
					INTEGER,
				diskAdapter
					DisplayString,
				diskPort
					INTEGER,
				diskTargetID
					INTEGER,
				diskLunID
					INTEGER,
				diskVendor
					DisplayString
			 }

		-- 1.3.6.1.4.1.674.10893.1.1.140.2.1.1
		diskNumber OBJECT-TYPE
			SYNTAX INTEGER (1..1000000000)
			ACCESS read-only
			STATUS mandatory
			DESCRIPTION
				"Instance number of the disk entry."
			::= { diskEntry 1 }


		-- 1.3.6.1.4.1.674.10893.1.1.140.2.1.2
		diskName OBJECT-TYPE
			SYNTAX DisplayString
			ACCESS read-only
			STATUS mandatory
			DESCRIPTION
				"The disk's name as represented in Array Manager."
			::= { diskEntry 2 }


		-- 1.3.6.1.4.1.674.10893.1.1.140.2.1.3
		diskVirtualDiskDeviceName OBJECT-TYPE
			SYNTAX DisplayString
			ACCESS read-only
			STATUS mandatory
			DESCRIPTION
				"Device name of the virtual disk that includes this disk.
				This is used to link the Disk to its virtual disk."
			::= { diskEntry 3 }


		-- 1.3.6.1.4.1.674.10893.1.1.140.2.1.4
		diskState OBJECT-TYPE
			SYNTAX INTEGER
				{
				ready(1),
				failed(2),
				online(3),
				offline(4),
				degraded(6),
				rebuild(24),
				noMedia(25),
				notReady(40)
				}
			ACCESS read-only
			STATUS mandatory
			DESCRIPTION
				"The current state of the Disk.
				Possible states:
				 0: Unknown
				 1: Ready
				 2: Failed
				 3: Online - The disk is accessible and has no known problems.
				 4: Offline
				 6: Degraded
				24: Rebuild
				25: No Media
				40: Not Ready"
			::= { diskEntry 4 }


		-- 1.3.6.1.4.1.674.10893.1.1.140.2.1.5
		diskSeverity OBJECT-TYPE
			SYNTAX INTEGER
				{
				warning(1),
				error(2),
				failure(3)
				}
			ACCESS read-only
			STATUS mandatory
			DESCRIPTION
				"Seriousness of the disk state.
				Possible values:
				0: OK
				1: Warning
				2: Error
				3: Failure"
			::= { diskEntry 5 }


		-- 1.3.6.1.4.1.674.10893.1.1.140.2.1.6
		diskLdmDeviceType OBJECT-TYPE
			SYNTAX INTEGER
				{
				dynamic(1),
				removable(2),
				cd-rom(3),
				basic(4),
				basicNoSignature(5),
				oem(6),
				dvd(7)
				}
			ACCESS read-only
			STATUS mandatory
			DESCRIPTION
				"The disk's LDM device type.
				Possible values:
				1: Dynamic
				2: Removable
				3: CD-ROM
				4: Basic
				5: Basic with no signature
				6: OEM
				7: DVD"
			::= { diskEntry 6 }


		-- 1.3.6.1.4.1.674.10893.1.1.140.2.1.7
		diskDgName OBJECT-TYPE
			SYNTAX DisplayString
			ACCESS read-only
			STATUS mandatory
			DESCRIPTION
				"The name identifying the disk type."
			::= { diskEntry 7 }


		-- 1.3.6.1.4.1.674.10893.1.1.140.2.1.8
		diskLengthInMB OBJECT-TYPE
			SYNTAX INTEGER
			ACCESS read-only
			STATUS mandatory
			DESCRIPTION
				"Length of the disk in megabytes. If this size is 0, it is
				smaller than a megabyte."
			::= { diskEntry 8 }


		-- 1.3.6.1.4.1.674.10893.1.1.140.2.1.9
		diskLengthInBytes OBJECT-TYPE
			SYNTAX INTEGER
			ACCESS read-only
			STATUS mandatory
			DESCRIPTION
				"The portion in bytes of the disk length that is less than
				a megabyte. This size plus the diskLengthInMB is the
				total length of the disk."
			::= { diskEntry 9 }


		-- 1.3.6.1.4.1.674.10893.1.1.140.2.1.10
		diskFreeSpaceInMB OBJECT-TYPE
			SYNTAX INTEGER
			ACCESS read-only
			STATUS mandatory
			DESCRIPTION
				"The amount of free space on this disk in megabytes. If
				this size is 0, it is smaller than a megabyte."
			::= { diskEntry 10 }


		-- 1.3.6.1.4.1.674.10893.1.1.140.2.1.11
		diskFreeSpaceInBytes OBJECT-TYPE
			SYNTAX INTEGER
			ACCESS read-only
			STATUS mandatory
			DESCRIPTION
				"The portion in bytes of the disk free space that is less
				than a megabyte. This size plus the diskFreeSpaceInMB
				is the total free space on the disk."
			::= { diskEntry 11 }


		-- 1.3.6.1.4.1.674.10893.1.1.140.2.1.12
		diskAdapter OBJECT-TYPE
			SYNTAX DisplayString
			ACCESS read-only
			STATUS mandatory
			DESCRIPTION
				"The name of the controller to which the device(s) represented
				by this disk object are connected."
			::= { diskEntry 12 }


		-- 1.3.6.1.4.1.674.10893.1.1.140.2.1.13
		diskPort OBJECT-TYPE
			SYNTAX INTEGER
			ACCESS read-only
			STATUS mandatory
			DESCRIPTION
				"The disk's port number as represented in Array Manager."
			::= { diskEntry 13 }


		-- 1.3.6.1.4.1.674.10893.1.1.140.2.1.14
		diskTargetID OBJECT-TYPE
			SYNTAX INTEGER
			ACCESS read-only
			STATUS mandatory
			DESCRIPTION
				"The disk's target ID as represented in Array Manager."
			::= { diskEntry 14 }


		-- 1.3.6.1.4.1.674.10893.1.1.140.2.1.15
		diskLunID OBJECT-TYPE
			SYNTAX INTEGER
			ACCESS read-only
			STATUS mandatory
			DESCRIPTION
				"The disk's LUN ID as represented in Array Manager."
			::= { diskEntry 15 }


		-- 1.3.6.1.4.1.674.10893.1.1.140.2.1.16
		diskVendor OBJECT-TYPE
			SYNTAX DisplayString
			ACCESS read-only
			STATUS mandatory
			DESCRIPTION
				"The disk's (re)seller's name."
			::= { diskEntry 16 }


		-- 1.3.6.1.4.1.674.10893.1.1.140.3
		arrayDiskLogicalConnectionTable OBJECT-TYPE
			SYNTAX SEQUENCE OF ArrayDiskLogicalConnectionEntry
			ACCESS not-accessible
			STATUS mandatory
			DESCRIPTION
				"A table of the connections between array disks, the
				virtual disk to which they belong, and their
				associated logical disk. For each object in the table,
				its object number corresponds to an instance number in
				the appropriate MIB table for that object where all of
				the object properties can be found.


				"
			::= { logicalDevices 3 }


		-- 1.3.6.1.4.1.674.10893.1.1.140.3.1
		arrayDiskLogicalConnectionEntry OBJECT-TYPE
			SYNTAX ArrayDiskLogicalConnectionEntry
			ACCESS not-accessible
			STATUS mandatory
			INDEX { arrayDiskLogicalConnectionNumber }
			::= { arrayDiskLogicalConnectionTable 1 }


		ArrayDiskLogicalConnectionEntry ::=
			SEQUENCE {
				arrayDiskLogicalConnectionNumber
					INTEGER,
				arrayDiskLogicalConnectionArrayDiskName
					DisplayString,
				arrayDiskLogicalConnectionArrayDiskNumber
					INTEGER,
				arrayDiskLogicalConnectionVirtualDiskName
					DisplayString,
				arrayDiskLogicalConnectionVirtualDiskNumber
					INTEGER,
				arrayDiskLogicalConnectionDiskName
					DisplayString,
				arrayDiskLogicalConnectionDiskNumber
					INTEGER
			 }

		-- 1.3.6.1.4.1.674.10893.1.1.140.3.1.1
		arrayDiskLogicalConnectionNumber OBJECT-TYPE
			SYNTAX INTEGER (1..1000000000)
			ACCESS read-only
			STATUS mandatory
			DESCRIPTION
				"Instance number of this array disk logical connection entry."
			::= { arrayDiskLogicalConnectionEntry 1 }


		-- 1.3.6.1.4.1.674.10893.1.1.140.3.1.2
		arrayDiskLogicalConnectionArrayDiskName OBJECT-TYPE
			SYNTAX DisplayString
			ACCESS read-only
			STATUS mandatory
			DESCRIPTION
				"The name of the array disk in this logical connection."
			::= { arrayDiskLogicalConnectionEntry 2 }


		-- 1.3.6.1.4.1.674.10893.1.1.140.3.1.3
		arrayDiskLogicalConnectionArrayDiskNumber OBJECT-TYPE
			SYNTAX INTEGER
			ACCESS read-only
			STATUS mandatory
			DESCRIPTION
				"The instance number of the array disk in this
				logical connection."
			::= { arrayDiskLogicalConnectionEntry 3 }


		-- 1.3.6.1.4.1.674.10893.1.1.140.3.1.4
		arrayDiskLogicalConnectionVirtualDiskName OBJECT-TYPE
			SYNTAX DisplayString
			ACCESS read-only
			STATUS mandatory
			DESCRIPTION
				"The name of the virtual disk to which this array disk
				belongs."
			::= { arrayDiskLogicalConnectionEntry 4 }


		-- 1.3.6.1.4.1.674.10893.1.1.140.3.1.5
		arrayDiskLogicalConnectionVirtualDiskNumber OBJECT-TYPE
			SYNTAX INTEGER
			ACCESS read-only
			STATUS mandatory
			DESCRIPTION
				"The instance number of the virtual disk to which this
				array disk belongs."
			::= { arrayDiskLogicalConnectionEntry 5 }


		-- 1.3.6.1.4.1.674.10893.1.1.140.3.1.6
		arrayDiskLogicalConnectionDiskName OBJECT-TYPE
			SYNTAX DisplayString
			ACCESS read-only
			STATUS mandatory
			DESCRIPTION
				"The name of the disk group to with this array disk
				belongs."
			::= { arrayDiskLogicalConnectionEntry 6 }


		-- 1.3.6.1.4.1.674.10893.1.1.140.3.1.7
		arrayDiskLogicalConnectionDiskNumber OBJECT-TYPE
			SYNTAX INTEGER
			ACCESS read-only
			STATUS mandatory
			DESCRIPTION
				"This instance number of the disk group to with this
				array disk belongs.
				"
			::= { arrayDiskLogicalConnectionEntry 7 }


		-- 1.3.6.1.4.1.674.10893.1.1.140.4
		subDiskTable OBJECT-TYPE
			SYNTAX SEQUENCE OF SubDiskEntry
			ACCESS not-accessible
			STATUS mandatory
			::= { logicalDevices 4 }


		-- 1.3.6.1.4.1.674.10893.1.1.140.4.1
		subDiskEntry OBJECT-TYPE
			SYNTAX SubDiskEntry
			ACCESS not-accessible
			STATUS mandatory
			INDEX { subDiskNumber }
			::= { subDiskTable 1 }


		SubDiskEntry ::=
			SEQUENCE {
				subDiskNumber
					INTEGER,
				subDiskName
					DisplayString,
				subDiskState
					INTEGER,
				subDiskSeverity
					INTEGER,
				subDiskLengthInMB
					INTEGER,
				subDiskLengthInBytes
					INTEGER
			 }

		-- 1.3.6.1.4.1.674.10893.1.1.140.4.1.1
		subDiskNumber OBJECT-TYPE
			SYNTAX INTEGER (1..1000000)
			ACCESS read-only
			STATUS mandatory
			::= { subDiskEntry 1 }


		-- 1.3.6.1.4.1.674.10893.1.1.140.4.1.2
		subDiskName OBJECT-TYPE
			SYNTAX DisplayString
			ACCESS read-only
			STATUS mandatory
			DESCRIPTION
				"The name identifying this sub-disk."
			::= { subDiskEntry 2 }


		-- 1.3.6.1.4.1.674.10893.1.1.140.4.1.3
		subDiskState OBJECT-TYPE
			SYNTAX INTEGER
				{
				ready(1),
				failed(2),
				online(3),
				offline(4),
				degraded(6)
				}
			ACCESS read-only
			STATUS mandatory
			DESCRIPTION
				"The current state of the sub-disk.
				Possible states:
				 0: Unknown
				 1: Ready
				 2: Failed
				 3: Online - The disk is accessible and has no known problems.
				 4: Offline
				 6: Degraded"
			::= { subDiskEntry 3 }


		-- 1.3.6.1.4.1.674.10893.1.1.140.4.1.4
		subDiskSeverity OBJECT-TYPE
			SYNTAX INTEGER
			ACCESS read-only
			STATUS mandatory
			DESCRIPTION
				"Severity of the sub-disk state.
				Possible values:
				0: OK
				1: Warning
				2: Error
				3: Failure"
			::= { subDiskEntry 4 }


		-- 1.3.6.1.4.1.674.10893.1.1.140.4.1.5
		subDiskLengthInMB OBJECT-TYPE
			SYNTAX INTEGER
			ACCESS read-only
			STATUS mandatory
			DESCRIPTION
				"Length of the sub-disk in megabytes. If this size is 0,
				it is smaller than a megabyte."
			::= { subDiskEntry 5 }


		-- 1.3.6.1.4.1.674.10893.1.1.140.4.1.6
		subDiskLengthInBytes OBJECT-TYPE
			SYNTAX INTEGER
			ACCESS read-only
			STATUS mandatory
			DESCRIPTION
				"The portion in bytes of the sub-disk length that is less
				than a megabyte. This size plus the subDiskLengthInMB is
				the total length of the sub-disk."
			::= { subDiskEntry 6 }


		-- 1.3.6.1.4.1.674.10893.1.1.140.5
		partitionTable OBJECT-TYPE
			SYNTAX SEQUENCE OF PartitionEntry
			ACCESS not-accessible
			STATUS mandatory
			::= { logicalDevices 5 }


		-- 1.3.6.1.4.1.674.10893.1.1.140.5.1
		partitionEntry OBJECT-TYPE
			SYNTAX PartitionEntry
			ACCESS not-accessible
			STATUS mandatory
			INDEX { partitionNumber }
			::= { partitionTable 1 }


		PartitionEntry ::=
			SEQUENCE {
				partitionNumber
					INTEGER,
				partitionName
					DisplayString,
				partitionState
					INTEGER,
				partitionSeverity
					INTEGER,
				partitionLengthInMB
					INTEGER,
				partitionLengthInBytes
					INTEGER,
				partitionLdmVolumeType
					INTEGER
			 }

		-- 1.3.6.1.4.1.674.10893.1.1.140.5.1.1
		partitionNumber OBJECT-TYPE
			SYNTAX INTEGER (1..255)
			ACCESS read-only
			STATUS mandatory
			DESCRIPTION
				"Instance number of the partition entry."
			::= { partitionEntry 1 }


		-- 1.3.6.1.4.1.674.10893.1.1.140.5.1.2
		partitionName OBJECT-TYPE
			SYNTAX DisplayString
			ACCESS read-only
			STATUS mandatory
			DESCRIPTION
				"The partition's name as represented in Array Manager."
			::= { partitionEntry 2 }


		-- 1.3.6.1.4.1.674.10893.1.1.140.5.1.3
		partitionState OBJECT-TYPE
			SYNTAX INTEGER
				{
				ready(1),
				failed(2),
				online(3),
				degraded(6)
				}
			ACCESS read-only
			STATUS mandatory
			DESCRIPTION
				"The state of the partition.
				Possible states:
				0: Unknown
				1: Ready
				2: Failed
				3: Online
				6: Degraded"
			::= { partitionEntry 3 }


		-- 1.3.6.1.4.1.674.10893.1.1.140.5.1.4
		partitionSeverity OBJECT-TYPE
			SYNTAX INTEGER
				{
				warning(1),
				error(2),
				failure(3)
				}
			ACCESS read-only
			STATUS mandatory
			DESCRIPTION
				"Severity of the partition state.
				Possible values:
				0: OK
				1: Warning
				2: Error
				3: Failure"
			::= { partitionEntry 4 }


		-- 1.3.6.1.4.1.674.10893.1.1.140.5.1.5
		partitionLengthInMB OBJECT-TYPE
			SYNTAX INTEGER
			ACCESS read-only
			STATUS mandatory
			DESCRIPTION
				"The length of the partition in megabytes. If this size is
				0, it is smaller than a megabyte."
			::= { partitionEntry 5 }


		-- 1.3.6.1.4.1.674.10893.1.1.140.5.1.6
		partitionLengthInBytes OBJECT-TYPE
			SYNTAX INTEGER
			ACCESS read-only
			STATUS mandatory
			DESCRIPTION
				"The portion of the partition length that is less than a
				megabyte. This size plus the partitionLengthInMB is the
				total length of the partition."
			::= { partitionEntry 6 }


		-- 1.3.6.1.4.1.674.10893.1.1.140.5.1.7
		partitionLdmVolumeType OBJECT-TYPE
			SYNTAX INTEGER
				{
				basic(1),
				extended(2),
				logical(3),
				cdrom(4),
				simple(5),
				stripe(6),
				mirror(7),
				raid5(8),
				span(9),
				dynamic(10)
				}
			ACCESS read-only
			STATUS mandatory
			DESCRIPTION
				"The partition's LDM volume type.
				Possible values:
				1: Basic - standard DOS/Windows disk signature
				2: Extended
				3: Logical
				4: CD ROM
				5: Simple
				6: Stripe
				7: Mirror
				8: Raid5
				9: Span
				10: Dynamic - upgraded disk"
			::= { partitionEntry 7 }


		-- 1.3.6.1.4.1.674.10893.1.1.140.6
		extendedPartitionTable OBJECT-TYPE
			SYNTAX SEQUENCE OF ExtendedPartitionEntry
			ACCESS not-accessible
			STATUS mandatory
			::= { logicalDevices 6 }


		-- 1.3.6.1.4.1.674.10893.1.1.140.6.1
		extendedPartitionEntry OBJECT-TYPE
			SYNTAX ExtendedPartitionEntry
			ACCESS not-accessible
			STATUS mandatory
			INDEX { extendedPartitionNumber }
			::= { extendedPartitionTable 1 }


		ExtendedPartitionEntry ::=
			SEQUENCE {
				extendedPartitionNumber
					INTEGER,
				extendedPartitionName
					DisplayString,
				extendedPartitionState
					INTEGER,
				extendedPartitionSeverity
					INTEGER
			 }

		-- 1.3.6.1.4.1.674.10893.1.1.140.6.1.1
		extendedPartitionNumber OBJECT-TYPE
			SYNTAX INTEGER (1..1000000)
			ACCESS read-only
			STATUS mandatory
			DESCRIPTION
				"The instance number of this extended partition entry."
			::= { extendedPartitionEntry 1 }


		-- 1.3.6.1.4.1.674.10893.1.1.140.6.1.2
		extendedPartitionName OBJECT-TYPE
			SYNTAX DisplayString
			ACCESS read-only
			STATUS mandatory
			DESCRIPTION
				"The name of this extended partition as represented in
				Array Manager"
			::= { extendedPartitionEntry 2 }


		-- 1.3.6.1.4.1.674.10893.1.1.140.6.1.3
		extendedPartitionState OBJECT-TYPE
			SYNTAX INTEGER
				{
				ready(1),
				failed(2),
				online(3),
				degraded(6)
				}
			ACCESS read-only
			STATUS mandatory
			DESCRIPTION
				"The current state of the extended partition.
				Possible states:
				0: Unknown
				1: Ready
				2: Failed
				3: Online
				6: Degraded"
			::= { extendedPartitionEntry 3 }


		-- 1.3.6.1.4.1.674.10893.1.1.140.6.1.4
		extendedPartitionSeverity OBJECT-TYPE
			SYNTAX INTEGER
				{
				warning(1),
				error(2),
				failure(3)
				}
			ACCESS read-only
			STATUS mandatory
			DESCRIPTION
				"Seriousness of the extended partition state.
				Possible values:
				0: OK
				1: Warning
				2: Error
				3: Failure"
			::= { extendedPartitionEntry 4 }


		-- 1.3.6.1.4.1.674.10893.1.1.140.7
		volumeTable OBJECT-TYPE
			SYNTAX SEQUENCE OF VolumeEntry
			ACCESS not-accessible
			STATUS mandatory
			DESCRIPTION
				"A table of volumes that are recognized by the operating
				system."
			::= { logicalDevices 7 }


		-- 1.3.6.1.4.1.674.10893.1.1.140.7.1
		volumeEntry OBJECT-TYPE
			SYNTAX VolumeEntry
			ACCESS not-accessible
			STATUS mandatory
			DESCRIPTION
				"An entry in the volume table. A row in this table cannot be
				created or deleted by SNMP operations on columns of the table."
			INDEX { volumeNumber }
			::= { volumeTable 1 }


		VolumeEntry ::=
			SEQUENCE {
				volumeNumber
					INTEGER,
				volumeDriveLetter
					DisplayString,
				volumeState
					INTEGER,
				volumeSeverity
					INTEGER,
				volumeLdmVolumeType
					INTEGER,
				volumeLabel
					DisplayString,
				volumeFSType
					DisplayString,
				volumeLengthInMB
					INTEGER,
				volumeLengthInBytes
					INTEGER,
				volumeFreeSpaceInMB
					INTEGER,
				volumeFreeSpaceInBytes
					INTEGER
			 }

		-- 1.3.6.1.4.1.674.10893.1.1.140.7.1.1
		volumeNumber OBJECT-TYPE
			SYNTAX INTEGER (1..255)
			ACCESS read-only
			STATUS mandatory
			DESCRIPTION
				"Instance number of the volume entry."
			::= { volumeEntry 1 }


		-- 1.3.6.1.4.1.674.10893.1.1.140.7.1.2
		volumeDriveLetter OBJECT-TYPE
			SYNTAX DisplayString (SIZE (1..255))
			ACCESS read-only
			STATUS mandatory
			DESCRIPTION
				"The volume's path (or drive letter) according to the
				operating system."
			::= { volumeEntry 2 }


		-- 1.3.6.1.4.1.674.10893.1.1.140.7.1.3
		volumeState OBJECT-TYPE
			SYNTAX INTEGER
				{
				ready(1),
				failed(2),
				online(3),
				offline(4),
				degraded(6),
				failedRedundancy(18),
				noMedia(25),
				formatting(26)
				}
			ACCESS read-only
			STATUS mandatory
			DESCRIPTION
				"The volume's current state.
				Possible states:
				 0: Unknown
				 1: Ready - The volume is accessible and has no known problems.
				 2: Failed - The volume cannot be started automatically.
				 3: Online
				 4: Offline
				 6: Degraded
				18: Failed Redundancy - The data on the volume is no longer fault tolerant because one of the underlying disks is not online.
				25: No Media
				26: Formatting - The volume is being formatted using the specifications you chose for formatting.

				?: Initializing - The volume is being initialized.
				?: Resynching - The volume's mirrors are being resynchronized so that both mirrors contain identical data.
				?: Regenerating - Data and parity are being regenerated for the RAID-5 volume.
				?: Failed Redundancy (At Risk) - The data on the volume is no longer fault tolerant, and I/O errors have been detected on the underlying disk
				?: No Media - No media has been inserted into the CD-ROM or removable drive. "
			::= { volumeEntry 3 }


		-- 1.3.6.1.4.1.674.10893.1.1.140.7.1.4
		volumeSeverity OBJECT-TYPE
			SYNTAX INTEGER
				{
				warning(1),
				error(2),
				failrue(3)
				}
			ACCESS read-only
			STATUS mandatory
			DESCRIPTION
				"The severity of the volume.
				Possible values:
				0: OK
				1: Warining
				2: Error
				3: Failure"
			::= { volumeEntry 4 }


		-- 1.3.6.1.4.1.674.10893.1.1.140.7.1.5
		volumeLdmVolumeType OBJECT-TYPE
			SYNTAX INTEGER
				{
				basic(1),
				extended(2),
				logical(3),
				cd-rom(4),
				simple(5),
				stripe(6),
				mirrror(7),
				raid5(8),
				span(9),
				dynamic(10)
				}
			ACCESS read-only
			STATUS mandatory
			DESCRIPTION
				"The volume's LMD volume type.
				Possible values:
				1: Basic - standard DOS/Windows disk signature
				2: Extended
				3: Logical
				4: CD ROM
				5: Simple
				6: Stripe
				7: Mirror
				8: Raid5
				9: Span
				10: Dynamic "
			::= { volumeEntry 5 }


		-- 1.3.6.1.4.1.674.10893.1.1.140.7.1.6
		volumeLabel OBJECT-TYPE
			SYNTAX DisplayString
			ACCESS read-only
			STATUS mandatory
			DESCRIPTION
				"The user definable label for this volume."
			::= { volumeEntry 6 }


		-- 1.3.6.1.4.1.674.10893.1.1.140.7.1.7
		volumeFSType OBJECT-TYPE
			SYNTAX DisplayString
			ACCESS read-only
			STATUS mandatory
			DESCRIPTION
				"The volume's operating system file system type.
				"
			::= { volumeEntry 7 }


		-- 1.3.6.1.4.1.674.10893.1.1.140.7.1.8
		volumeLengthInMB OBJECT-TYPE
			SYNTAX INTEGER
			ACCESS read-only
			STATUS mandatory
			DESCRIPTION
				"The size of the volume in megabytes. If this size is 0,
				it is smaller than a megabyte."
			::= { volumeEntry 8 }


		-- 1.3.6.1.4.1.674.10893.1.1.140.7.1.9
		volumeLengthInBytes OBJECT-TYPE
			SYNTAX INTEGER
			ACCESS read-only
			STATUS mandatory
			DESCRIPTION
				"The portion in bytes of the volume that is smaller than
				a megabyte. This size plus the volumeLengthInMB is the
				total length of the volume."
			::= { volumeEntry 9 }


		-- 1.3.6.1.4.1.674.10893.1.1.140.7.1.10
		volumeFreeSpaceInMB OBJECT-TYPE
			SYNTAX INTEGER
			ACCESS read-only
			STATUS mandatory
			DESCRIPTION
				"The amount of free space on the volume in megabytes. If
				this size if 0, it is smaller than a megabyte."
			::= { volumeEntry 10 }


		-- 1.3.6.1.4.1.674.10893.1.1.140.7.1.11
		volumeFreeSpaceInBytes OBJECT-TYPE
			SYNTAX INTEGER
			ACCESS read-only
			STATUS mandatory
			DESCRIPTION
				"The portion in bytes of the free space on the volume that
				is smaller than a megabyte. This size plus the
				volumeFreeSpaceInMB is the total length of the volume."
			::= { volumeEntry 11 }


		-- 1.3.6.1.4.1.674.10893.1.1.140.8
		plexTable OBJECT-TYPE
			SYNTAX SEQUENCE OF PlexEntry
			ACCESS not-accessible
			STATUS mandatory
			::= { logicalDevices 8 }


		-- 1.3.6.1.4.1.674.10893.1.1.140.8.1
		plexEntry OBJECT-TYPE
			SYNTAX PlexEntry
			ACCESS not-accessible
			STATUS mandatory
			INDEX { plexNumber }
			::= { plexTable 1 }


		PlexEntry ::=
			SEQUENCE {
				plexNumber
					INTEGER,
				plexName
					DisplayString,
				plexStripeWidthInMB
					INTEGER,
				plexStripeWidthInBytes
					INTEGER,
				plexColumns
					INTEGER,
				plexLayout
					INTEGER
			 }

		-- 1.3.6.1.4.1.674.10893.1.1.140.8.1.1
		plexNumber OBJECT-TYPE
			SYNTAX INTEGER (1..255)
			ACCESS read-only
			STATUS mandatory
			DESCRIPTION
				"Instance number of the plex entry."
			::= { plexEntry 1 }


		-- 1.3.6.1.4.1.674.10893.1.1.140.8.1.2
		plexName OBJECT-TYPE
			SYNTAX DisplayString
			ACCESS read-only
			STATUS mandatory
			DESCRIPTION
				"The name identifying this plex as represented in Array Manager."
			::= { plexEntry 2 }


		-- 1.3.6.1.4.1.674.10893.1.1.140.8.1.3
		plexStripeWidthInMB OBJECT-TYPE
			SYNTAX INTEGER
			ACCESS read-only
			STATUS mandatory
			DESCRIPTION
				"The width of the plex stripe in megabytes. If this size
				is 0, it is smaller than a megabyte."
			::= { plexEntry 3 }


		-- 1.3.6.1.4.1.674.10893.1.1.140.8.1.4
		plexStripeWidthInBytes OBJECT-TYPE
			SYNTAX INTEGER
			ACCESS read-only
			STATUS mandatory
			DESCRIPTION
				"The portion in bytes of the plex stripe that is smaller
				than a megabyte. This size plus the plexStripeWidthInMB
				is the total size of the stripe."
			::= { plexEntry 4 }


		-- 1.3.6.1.4.1.674.10893.1.1.140.8.1.5
		plexColumns OBJECT-TYPE
			SYNTAX INTEGER
			ACCESS read-only
			STATUS mandatory
			DESCRIPTION
				"The number of columns in one plex."
			::= { plexEntry 5 }


		-- 1.3.6.1.4.1.674.10893.1.1.140.8.1.6
		plexLayout OBJECT-TYPE
			SYNTAX INTEGER
				{
				stripedSubdisks(1),
				concatenatedSubdisks(2),
				raidLayout(3)
				}
			ACCESS read-only
			STATUS mandatory
			DESCRIPTION
				"The type of RAID of this plex.
				Possible values:
				1: Striped Subdisks
				2: Concatenated Subdisks
				3: RAID layout "
			::= { plexEntry 6 }


		-- 1.3.6.1.4.1.674.10893.1.1.140.9
		basicDiskExtendedConnectionTable OBJECT-TYPE
			SYNTAX SEQUENCE OF BasicDiskExtendedConnectionEntry
			ACCESS not-accessible
			STATUS mandatory
			DESCRIPTION
				"A table of the connections between array disks, the
				virtual disk to which they belong, their associated
				logical basic disk, extended partition, partition and
				volume.  For each object in the table, its object number
				corresponds to an instance number in the appropriate
				MIB table for that object where all of the object
				properties can be found.
				"
			::= { logicalDevices 9 }


		-- 1.3.6.1.4.1.674.10893.1.1.140.9.1
		basicDiskExtendedConnectionEntry OBJECT-TYPE
			SYNTAX BasicDiskExtendedConnectionEntry
			ACCESS not-accessible
			STATUS mandatory
			INDEX { basicDiskExtendedConnectionNumber }
			::= { basicDiskExtendedConnectionTable 1 }


		BasicDiskExtendedConnectionEntry ::=
			SEQUENCE {
				basicDiskExtendedConnectionNumber
					INTEGER,
				basicDiskExtendedConnectionArrayDiskName
					DisplayString,
				basicDiskExtendedConnectionArrayDiskNumber
					INTEGER,
				basicDiskExtendedConnectionVirtualDiskName
					DisplayString,
				basicDiskExtendedConnectionVirtualDiskNumber
					INTEGER,
				basicDiskExtendedConnectionDiskName
					DisplayString,
				basicDiskExtendedConnectionDiskNumber
					INTEGER,
				basicDiskExtendedConnectionExtendedPartitionName
					DisplayString,
				basicDiskExtendedConnectionExtendedPartitionNumber
					INTEGER,
				basicDiskExtendedConnectionPartitionName
					DisplayString,
				basicDiskExtendedConnectionPartitionNumber
					INTEGER,
				basicDiskExtendedConnectionVolumeDriveLetter
					DisplayString,
				basicDiskExtendedConnectionVolumeNumber
					INTEGER
			 }

		-- 1.3.6.1.4.1.674.10893.1.1.140.9.1.1
		basicDiskExtendedConnectionNumber OBJECT-TYPE
			SYNTAX INTEGER (1..1000000)
			ACCESS read-only
			STATUS mandatory
			DESCRIPTION
				"Instance number of this basic disk connection entry."
			::= { basicDiskExtendedConnectionEntry 1 }


		-- 1.3.6.1.4.1.674.10893.1.1.140.9.1.2
		basicDiskExtendedConnectionArrayDiskName OBJECT-TYPE
			SYNTAX DisplayString
			ACCESS read-only
			STATUS mandatory
			DESCRIPTION
				"The name of an array disk that is part of the basic disk
				in this connection table entry."
			::= { basicDiskExtendedConnectionEntry 2 }


		-- 1.3.6.1.4.1.674.10893.1.1.140.9.1.3
		basicDiskExtendedConnectionArrayDiskNumber OBJECT-TYPE
			SYNTAX INTEGER
			ACCESS read-only
			STATUS mandatory
			DESCRIPTION
				"The instance number in the arrayDiskTable of the array
				disk in this basic disk connection entry."
			::= { basicDiskExtendedConnectionEntry 3 }


		-- 1.3.6.1.4.1.674.10893.1.1.140.9.1.4
		basicDiskExtendedConnectionVirtualDiskName OBJECT-TYPE
			SYNTAX DisplayString
			ACCESS read-only
			STATUS mandatory
			DESCRIPTION
				"The name of the virtual disk that is part of the basic disk
				in this connection table entry."
			::= { basicDiskExtendedConnectionEntry 4 }


		-- 1.3.6.1.4.1.674.10893.1.1.140.9.1.5
		basicDiskExtendedConnectionVirtualDiskNumber OBJECT-TYPE
			SYNTAX INTEGER
			ACCESS read-only
			STATUS mandatory
			DESCRIPTION
				"The instance number in the virtualDiskTable of this virtual
				disk that is part of the basic disk."
			::= { basicDiskExtendedConnectionEntry 5 }


		-- 1.3.6.1.4.1.674.10893.1.1.140.9.1.6
		basicDiskExtendedConnectionDiskName OBJECT-TYPE
			SYNTAX DisplayString
			ACCESS read-only
			STATUS mandatory
			DESCRIPTION
				"The name of the basic disk in this connection table entry."
			::= { basicDiskExtendedConnectionEntry 6 }


		-- 1.3.6.1.4.1.674.10893.1.1.140.9.1.7
		basicDiskExtendedConnectionDiskNumber OBJECT-TYPE
			SYNTAX INTEGER
			ACCESS read-only
			STATUS mandatory
			DESCRIPTION
				"The instance number in the diskTable of the disk in this
				conneciton table entry."
			::= { basicDiskExtendedConnectionEntry 7 }


		-- 1.3.6.1.4.1.674.10893.1.1.140.9.1.8
		basicDiskExtendedConnectionExtendedPartitionName OBJECT-TYPE
			SYNTAX DisplayString
			ACCESS read-only
			STATUS mandatory
			DESCRIPTION
				"The name of the extended partition that is part of the
				basic disk in this connection table entry."
			::= { basicDiskExtendedConnectionEntry 8 }


		-- 1.3.6.1.4.1.674.10893.1.1.140.9.1.9
		basicDiskExtendedConnectionExtendedPartitionNumber OBJECT-TYPE
			SYNTAX INTEGER
			ACCESS read-only
			STATUS mandatory
			DESCRIPTION
				"The instance number in the extendedPartitionTable of this
				extended partition that is part of the basic disk."
			::= { basicDiskExtendedConnectionEntry 9 }


		-- 1.3.6.1.4.1.674.10893.1.1.140.9.1.10
		basicDiskExtendedConnectionPartitionName OBJECT-TYPE
			SYNTAX DisplayString
			ACCESS read-only
			STATUS mandatory
			DESCRIPTION
				"The name of the partition that is part of the
				basic disk in this connection table entry."
			::= { basicDiskExtendedConnectionEntry 10 }


		-- 1.3.6.1.4.1.674.10893.1.1.140.9.1.11
		basicDiskExtendedConnectionPartitionNumber OBJECT-TYPE
			SYNTAX INTEGER
			ACCESS read-only
			STATUS mandatory
			DESCRIPTION
				"The instance number in the partitionTable of this
				partition that is part of the basic disk."
			::= { basicDiskExtendedConnectionEntry 11 }


		-- 1.3.6.1.4.1.674.10893.1.1.140.9.1.12
		basicDiskExtendedConnectionVolumeDriveLetter OBJECT-TYPE
			SYNTAX DisplayString
			ACCESS read-only
			STATUS mandatory
			DESCRIPTION
				"The path (or drive letter) of the volume to which this
				basic disk belongs."
			::= { basicDiskExtendedConnectionEntry 12 }


		-- 1.3.6.1.4.1.674.10893.1.1.140.9.1.13
		basicDiskExtendedConnectionVolumeNumber OBJECT-TYPE
			SYNTAX INTEGER
			ACCESS read-only
			STATUS mandatory
			DESCRIPTION
				"The instance number in the volumeTable of the volume to
				which this basic disk belongs."
			::= { basicDiskExtendedConnectionEntry 13 }


		-- 1.3.6.1.4.1.674.10893.1.1.140.10
		basicDiskNonExtendedConnectionTable OBJECT-TYPE
			SYNTAX SEQUENCE OF BasicDiskNonExtendedConnectionEntry
			ACCESS not-accessible
			STATUS mandatory
			DESCRIPTION
				"A table of the connections between array disks, the
				virtual disk to which they belong, their associated
				logical basic disk, partition and volume. For each
				object in the table, its object number corresponds to an
				instance number in the appropriate MIB table for that
				object where all of the object properties can be found."
			::= { logicalDevices 10 }


		-- 1.3.6.1.4.1.674.10893.1.1.140.10.1
		basicDiskNonExtendedConnectionEntry OBJECT-TYPE
			SYNTAX BasicDiskNonExtendedConnectionEntry
			ACCESS not-accessible
			STATUS mandatory
			INDEX { basicDiskNonExtendedConnectionNumber }
			::= { basicDiskNonExtendedConnectionTable 1 }


		BasicDiskNonExtendedConnectionEntry ::=
			SEQUENCE {
				basicDiskNonExtendedConnectionNumber
					INTEGER,
				basicDiskNonExtendedConnectionArrayDiskName
					DisplayString,
				basicDiskNonExtendedConnectionArrayDiskNumber
					INTEGER,
				basicDiskNonExtendedConnectionVirtualDiskName
					DisplayString,
				basicDiskNonExtendedConnectionVirtualDiskNumber
					INTEGER,
				basicDiskNonExtendedConnectionDiskName
					DisplayString,
				basicDiskNonExtendedConnectionDiskNumber
					INTEGER,
				basicDiskNonExtendedConnectionPartitionName
					DisplayString,
				basicDiskNonExtendedConnectionPartitionNumber
					INTEGER,
				basicDiskNonExtendedConnectionVolumeDriveLetter
					DisplayString,
				basicDiskNonExtendedConnectionVolumeNumber
					INTEGER
			 }

		-- 1.3.6.1.4.1.674.10893.1.1.140.10.1.1
		basicDiskNonExtendedConnectionNumber OBJECT-TYPE
			SYNTAX INTEGER (1..1000000)
			ACCESS read-only
			STATUS mandatory
			DESCRIPTION
				"Instance number of this basic disk connection entry."
			::= { basicDiskNonExtendedConnectionEntry 1 }


		-- 1.3.6.1.4.1.674.10893.1.1.140.10.1.2
		basicDiskNonExtendedConnectionArrayDiskName OBJECT-TYPE
			SYNTAX DisplayString
			ACCESS read-only
			STATUS mandatory
			DESCRIPTION
				"The name of an array disk that is part of the basic disk
				in this connection table entry."
			::= { basicDiskNonExtendedConnectionEntry 2 }


		-- 1.3.6.1.4.1.674.10893.1.1.140.10.1.3
		basicDiskNonExtendedConnectionArrayDiskNumber OBJECT-TYPE
			SYNTAX INTEGER
			ACCESS read-only
			STATUS mandatory
			DESCRIPTION
				"The instance number in the arrayDiskTable of the array
				disk in this basic disk connection entry."
			::= { basicDiskNonExtendedConnectionEntry 3 }


		-- 1.3.6.1.4.1.674.10893.1.1.140.10.1.4
		basicDiskNonExtendedConnectionVirtualDiskName OBJECT-TYPE
			SYNTAX DisplayString
			ACCESS read-only
			STATUS mandatory
			DESCRIPTION
				"The name of the virtual disk that is part of the basic disk
				in this connection table entry."
			::= { basicDiskNonExtendedConnectionEntry 4 }


		-- 1.3.6.1.4.1.674.10893.1.1.140.10.1.5
		basicDiskNonExtendedConnectionVirtualDiskNumber OBJECT-TYPE
			SYNTAX INTEGER
			ACCESS read-only
			STATUS mandatory
			DESCRIPTION
				"The instance number in the virtualDiskTable of this virtual
				disk that is part of the basic disk."
			::= { basicDiskNonExtendedConnectionEntry 5 }


		-- 1.3.6.1.4.1.674.10893.1.1.140.10.1.6
		basicDiskNonExtendedConnectionDiskName OBJECT-TYPE
			SYNTAX DisplayString
			ACCESS read-only
			STATUS mandatory
			DESCRIPTION
				"The name of the basic disk in this connection table entry."
			::= { basicDiskNonExtendedConnectionEntry 6 }


		-- 1.3.6.1.4.1.674.10893.1.1.140.10.1.7
		basicDiskNonExtendedConnectionDiskNumber OBJECT-TYPE
			SYNTAX INTEGER
			ACCESS read-only
			STATUS mandatory
			DESCRIPTION
				"The instance number in the diskTable of the disk in this
				conneciton table entry."
			::= { basicDiskNonExtendedConnectionEntry 7 }


		-- 1.3.6.1.4.1.674.10893.1.1.140.10.1.8
		basicDiskNonExtendedConnectionPartitionName OBJECT-TYPE
			SYNTAX DisplayString
			ACCESS read-only
			STATUS mandatory
			DESCRIPTION
				"The name of the partition that is part of the
				basic disk in this connection table entry."
			::= { basicDiskNonExtendedConnectionEntry 8 }


		-- 1.3.6.1.4.1.674.10893.1.1.140.10.1.9
		basicDiskNonExtendedConnectionPartitionNumber OBJECT-TYPE
			SYNTAX INTEGER
			ACCESS read-only
			STATUS mandatory
			DESCRIPTION
				"The instance number in the partitionTable of this
				partition that is part of the basic disk."
			::= { basicDiskNonExtendedConnectionEntry 9 }


		-- 1.3.6.1.4.1.674.10893.1.1.140.10.1.10
		basicDiskNonExtendedConnectionVolumeDriveLetter OBJECT-TYPE
			SYNTAX DisplayString
			ACCESS read-only
			STATUS mandatory
			DESCRIPTION
				"The path (or drive letter) of the volume to which this
				basic disk belongs."
			::= { basicDiskNonExtendedConnectionEntry 10 }


		-- 1.3.6.1.4.1.674.10893.1.1.140.10.1.11
		basicDiskNonExtendedConnectionVolumeNumber OBJECT-TYPE
			SYNTAX INTEGER
			ACCESS read-only
			STATUS mandatory
			DESCRIPTION
				"The instance number in the volumeTable of the volume to
				which this basic disk belongs."
			::= { basicDiskNonExtendedConnectionEntry 11 }


		-- 1.3.6.1.4.1.674.10893.1.1.140.11
		dynamicDiskConnectionTable OBJECT-TYPE
			SYNTAX SEQUENCE OF DynamicDiskConnectionEntry
			ACCESS not-accessible
			STATUS mandatory
			DESCRIPTION
				"A table of the connections between array disks, the
				virtual disk to which they belong, their associated
				logical dynamic disk, sub-disk, plex and volume.
				For each object in the table, its object number
				corresponds to an instance number in the appropriate
				MIB table for that object where all of the object
				properties can be found."
			::= { logicalDevices 11 }


		-- 1.3.6.1.4.1.674.10893.1.1.140.11.1
		dynamicDiskConnectionEntry OBJECT-TYPE
			SYNTAX DynamicDiskConnectionEntry
			ACCESS not-accessible
			STATUS mandatory
			INDEX { dynamicDiskConnectionNumber }
			::= { dynamicDiskConnectionTable 1 }


		DynamicDiskConnectionEntry ::=
			SEQUENCE {
				dynamicDiskConnectionNumber
					INTEGER,
				dynamicDiskConnectionArrayDiskName
					DisplayString,
				dynamicDiskConnectionArrayDiskNumber
					INTEGER,
				dynamicDiskConnectionVirtualDiskName
					DisplayString,
				dynamicDiskConnectionVirtualDiskNumber
					INTEGER,
				dynamicDiskConnectionDiskName
					DisplayString,
				dynamicDiskConnectionDiskNumber
					INTEGER,
				dynamicDiskConnectionSubDiskName
					DisplayString,
				dynamicDiskConnectionSubDiskNumber
					INTEGER,
				dynamicDiskConnectionPlexName
					DisplayString,
				dynamicDiskConnectionPlexNumber
					INTEGER,
				dynamicDiskConnectionVolumeDriveLetter
					DisplayString,
				dynamicDiskConnectionVolumeNumber
					INTEGER
			 }

		-- 1.3.6.1.4.1.674.10893.1.1.140.11.1.1
		dynamicDiskConnectionNumber OBJECT-TYPE
			SYNTAX INTEGER (1..255)
			ACCESS read-only
			STATUS mandatory
			DESCRIPTION
				"Instance number of this dynamic disk connection entry."
			::= { dynamicDiskConnectionEntry 1 }


		-- 1.3.6.1.4.1.674.10893.1.1.140.11.1.2
		dynamicDiskConnectionArrayDiskName OBJECT-TYPE
			SYNTAX DisplayString
			ACCESS read-only
			STATUS mandatory
			DESCRIPTION
				"The name of an array disk that is part of the dynamic disk
				in this connection table entry."
			::= { dynamicDiskConnectionEntry 2 }


		-- 1.3.6.1.4.1.674.10893.1.1.140.11.1.3
		dynamicDiskConnectionArrayDiskNumber OBJECT-TYPE
			SYNTAX INTEGER
			ACCESS read-only
			STATUS mandatory
			DESCRIPTION
				"The instance number in the arrayDiskTable of the array
				disk in this dynamic disk connection entry."
			::= { dynamicDiskConnectionEntry 3 }


		-- 1.3.6.1.4.1.674.10893.1.1.140.11.1.4
		dynamicDiskConnectionVirtualDiskName OBJECT-TYPE
			SYNTAX DisplayString
			ACCESS read-only
			STATUS mandatory
			DESCRIPTION
				"The name of the virtual disk that is part of the dynamic
				disk in this connection table entry."
			::= { dynamicDiskConnectionEntry 4 }


		-- 1.3.6.1.4.1.674.10893.1.1.140.11.1.5
		dynamicDiskConnectionVirtualDiskNumber OBJECT-TYPE
			SYNTAX INTEGER
			ACCESS read-only
			STATUS mandatory
			DESCRIPTION
				"The instance number in the virtualDiskTable of this virtual
				disk that is part of the dynamic disk."
			::= { dynamicDiskConnectionEntry 5 }


		-- 1.3.6.1.4.1.674.10893.1.1.140.11.1.6
		dynamicDiskConnectionDiskName OBJECT-TYPE
			SYNTAX DisplayString
			ACCESS read-only
			STATUS mandatory
			DESCRIPTION
				"The name of the dynamic disk in this connection table entry."
			::= { dynamicDiskConnectionEntry 6 }


		-- 1.3.6.1.4.1.674.10893.1.1.140.11.1.7
		dynamicDiskConnectionDiskNumber OBJECT-TYPE
			SYNTAX INTEGER
			ACCESS read-only
			STATUS mandatory
			DESCRIPTION
				"The instance number in the diskTable of the disk in this
				conneciton table entry."
			::= { dynamicDiskConnectionEntry 7 }


		-- 1.3.6.1.4.1.674.10893.1.1.140.11.1.8
		dynamicDiskConnectionSubDiskName OBJECT-TYPE
			SYNTAX DisplayString
			ACCESS read-only
			STATUS mandatory
			DESCRIPTION
				"The name of the dynamic sub-disk in this connection."
			::= { dynamicDiskConnectionEntry 8 }


		-- 1.3.6.1.4.1.674.10893.1.1.140.11.1.9
		dynamicDiskConnectionSubDiskNumber OBJECT-TYPE
			SYNTAX INTEGER
			ACCESS read-only
			STATUS mandatory
			DESCRIPTION
				"The instance number in the subDiskTable of the dynamic
				sub-disk in this connection."
			::= { dynamicDiskConnectionEntry 9 }


		-- 1.3.6.1.4.1.674.10893.1.1.140.11.1.10
		dynamicDiskConnectionPlexName OBJECT-TYPE
			SYNTAX DisplayString
			ACCESS read-only
			STATUS mandatory
			DESCRIPTION
				"The name of the plex to which this dynamic disk belongs."
			::= { dynamicDiskConnectionEntry 10 }


		-- 1.3.6.1.4.1.674.10893.1.1.140.11.1.11
		dynamicDiskConnectionPlexNumber OBJECT-TYPE
			SYNTAX INTEGER
			ACCESS read-write
			STATUS mandatory
			DESCRIPTION
				"The instance number in the plexTable of the plex to which
				this dynamic disk belongs.
				"
			::= { dynamicDiskConnectionEntry 11 }


		-- 1.3.6.1.4.1.674.10893.1.1.140.11.1.12
		dynamicDiskConnectionVolumeDriveLetter OBJECT-TYPE
			SYNTAX DisplayString
			ACCESS read-only
			STATUS mandatory
			DESCRIPTION
				"The path (or drive letter) of the volume to which this
				dynamic disk belongs."
			::= { dynamicDiskConnectionEntry 12 }


		-- 1.3.6.1.4.1.674.10893.1.1.140.11.1.13
		dynamicDiskConnectionVolumeNumber OBJECT-TYPE
			SYNTAX INTEGER
			ACCESS read-only
			STATUS mandatory
			DESCRIPTION
				"The instance number of the volume to which this dynamic
				disk belongs."
			::= { dynamicDiskConnectionEntry 13 }


		-- 1.3.6.1.4.1.674.10893.1.1.200
		aryMgrEvts OBJECT IDENTIFIER ::= { arrayManager 200 }


		-- 1.3.6.1.4.1.674.10893.1.1.200.201
		controllerNameEv OBJECT-TYPE
			SYNTAX DisplayString (SIZE (1..64))
			ACCESS read-only
			STATUS mandatory
			DESCRIPTION
				"Controller Name for which trap is generated."
			::= { aryMgrEvts 201 }


		-- 1.3.6.1.4.1.674.10893.1.1.200.202
		channelNumberEv OBJECT-TYPE
			SYNTAX INTEGER (0..3)
			ACCESS read-only
			STATUS mandatory
			DESCRIPTION
				"Channel Number for which trap is generated."
			::= { aryMgrEvts 202 }


		-- 1.3.6.1.4.1.674.10893.1.1.200.203
		targetIDEv OBJECT-TYPE
			SYNTAX INTEGER (0..15)
			ACCESS read-only
			STATUS mandatory
			DESCRIPTION
				"SCSI ID of the device for which trap is generated."
			::= { aryMgrEvts 203 }


		-- 1.3.6.1.4.1.674.10893.1.1.200.204
		virtualDiskNameEv OBJECT-TYPE
			SYNTAX DisplayString (SIZE (1..64))
			ACCESS read-only
			STATUS mandatory
			DESCRIPTION
				"Virtual Disk for which trap is generated."
			::= { aryMgrEvts 204 }


		-- 1.3.6.1.4.1.674.10893.1.1.200.205
		arrayDiskNameEv OBJECT-TYPE
			SYNTAX DisplayString (SIZE (1..64))
			ACCESS read-only
			STATUS mandatory
			DESCRIPTION
				"Array Disk for which trap is generated."
			::= { aryMgrEvts 205 }


		-- 1.3.6.1.4.1.674.10893.1.1.200.206
		oldVDConfigEv OBJECT-TYPE
			SYNTAX DisplayString (SIZE (1..128))
			ACCESS read-only
			STATUS mandatory
			DESCRIPTION
				"Current Virtual Disk configuration for which trap is generated"
			::= { aryMgrEvts 206 }


		-- 1.3.6.1.4.1.674.10893.1.1.200.207
		newVDConfigEv OBJECT-TYPE
			SYNTAX DisplayString (SIZE (1..128))
			ACCESS read-only
			STATUS mandatory
			DESCRIPTION
				"New Virtual Disk configuration for which trap is generated."
			::= { aryMgrEvts 207 }


		-- 1.3.6.1.4.1.674.10893.1.1.200.208
		enclosureNumberEv OBJECT-TYPE
			SYNTAX INTEGER
			ACCESS read-only
			STATUS mandatory
			DESCRIPTION
				"Enclosure Number for which trap is generated."
			::= { aryMgrEvts 208 }


		-- 1.3.6.1.4.1.674.10893.1.1.200.209
		unitNumberEv OBJECT-TYPE
			SYNTAX INTEGER
			ACCESS read-only
			STATUS mandatory
			DESCRIPTION
				"Unit Number for which trap is generated.
				(Fan, Power Supply, Temperature Probe)"
			::= { aryMgrEvts 209 }


		-- 1.3.6.1.4.1.674.10893.1.1.200.210
		enclosureNameEv OBJECT-TYPE
			SYNTAX DisplayString
			ACCESS read-only
			STATUS mandatory
			DESCRIPTION
				"Enclosure Name for which trap is generated."
			::= { aryMgrEvts 210 }


		-- 1.3.6.1.4.1.674.10893.1.1.200.211
		unitNameEv OBJECT-TYPE
			SYNTAX DisplayString
			ACCESS read-only
			STATUS mandatory
			DESCRIPTION
				"Unit Number for which trap is generated.
				(Fan, Power Supply, Temperature Probe)"
			::= { aryMgrEvts 211 }


		-- 1.3.6.1.4.1.674.10893.1.1.200.212
		timeEv OBJECT-TYPE
			SYNTAX INTEGER
			ACCESS read-only
			STATUS mandatory
			DESCRIPTION
				"Amount of time specified in the trap message."
			::= { aryMgrEvts 212 }


		-- 1.3.6.1.4.1.674.10893.1.1.200.213
		volumeNameEv OBJECT-TYPE
			SYNTAX DisplayString
			ACCESS read-only
			STATUS mandatory
			DESCRIPTION
				"Volume Drive Letter for which trap is generated."
			::= { aryMgrEvts 213 }


		-- 1.3.6.1.4.1.674.10893.1.1.200.214
		enclosureUnitNamesEv OBJECT-TYPE
			SYNTAX DisplayString
			ACCESS read-only
			STATUS mandatory
			DESCRIPTION
				"Combination of the enclosure name and unit number
				for which trap is generated."
			::= { aryMgrEvts 214 }


		-- 1.3.6.1.4.1.674.10893.1.1.200.215
		virtualDiskNameNewEv OBJECT-TYPE
			SYNTAX DisplayString
			ACCESS read-only
			STATUS mandatory
			DESCRIPTION
				"New name of the virtual disk for which trap is generated."
			::= { aryMgrEvts 215 }


		-- 1.3.6.1.4.1.674.10893.1.1.200.216
		device1NameEv OBJECT-TYPE
			SYNTAX DisplayString
			ACCESS read-only
			STATUS mandatory
			DESCRIPTION
				"Name of the device for which trap is generated.
				Note: The device type contained in this generic variable could change for different occurrences of a trap."
			::= { aryMgrEvts 216 }


		-- 1.3.6.1.4.1.674.10893.1.1.200.217
		senseKeyEv OBJECT-TYPE
			SYNTAX DisplayString
			ACCESS read-only
			STATUS mandatory
			DESCRIPTION
				"Sense Key data for this trap in hexidecimal."
			::= { aryMgrEvts 217 }


		-- 1.3.6.1.4.1.674.10893.1.1.200.218
		senseCodeEv OBJECT-TYPE
			SYNTAX DisplayString
			ACCESS read-only
			STATUS mandatory
			DESCRIPTION
				"Sense Code data for this trap in hexidecimal."
			::= { aryMgrEvts 218 }


		-- 1.3.6.1.4.1.674.10893.1.1.200.219
		senseQualifierEv OBJECT-TYPE
			SYNTAX DisplayString
			ACCESS read-only
			STATUS mandatory
			DESCRIPTION
				"Sense Qualifier data for this trap in hexidecimal."
			::= { aryMgrEvts 219 }


		-- 1.3.6.1.4.1.674.10893.1.1.200.220
		eMMFWVersion0Ev OBJECT-TYPE
			SYNTAX DisplayString
			ACCESS read-only
			STATUS mandatory
			DESCRIPTION
				"Firmware version for EMM 0."
			::= { aryMgrEvts 220 }


		-- 1.3.6.1.4.1.674.10893.1.1.200.221
		eMMFWVersion1Ev OBJECT-TYPE
			SYNTAX DisplayString
			ACCESS read-only
			STATUS mandatory
			DESCRIPTION
				"Firmware version for EMM 1."
			::= { aryMgrEvts 221 }


		-- 1.3.6.1.4.1.674.10893.1.1.200.222
		rebuildRateEv OBJECT-TYPE
			SYNTAX DisplayString
			ACCESS read-only
			STATUS mandatory
			DESCRIPTION
				"New rebuild rate for controller in this event."
			::= { aryMgrEvts 222 }



--
-- Trap definitions
--

		arrayDiskFailed TRAP-TYPE
			ENTERPRISE aryMgrEvts
			VARIABLES { controllerNameEv, arrayDiskNameEv }
			DESCRIPTION
				"%s, %s failed."
--#TYPE   "Array Manager Event: Array Disk Failed"
--#SUMMARY  "%s, %s failed."
--#CATEGORY "Error Events"
--#ARGUMENTS { 0, 1 }
--#SEVERITY CRITICAL
--#STATE   FAILED
--#STATUS  MANDATORY
			::= 500
		arrayDiskRemoved TRAP-TYPE
			ENTERPRISE aryMgrEvts
			VARIABLES { controllerNameEv, arrayDiskNameEv }
			DESCRIPTION
				"%s, %s removed."
--#TYPE   "Array Manager Event: Array Disk removed"
--#SUMMARY  "%s, %s removed."
--#CATEGORY "Status Events"
--#ARGUMENTS { 0, 1 }
--#SEVERITY MINOR
--#STATE   FAILED
--#STATUS  MANDATORY
			::= 501
		arrayDiskOffline TRAP-TYPE
			ENTERPRISE aryMgrEvts
			VARIABLES { controllerNameEv, arrayDiskNameEv }
			DESCRIPTION
				"%s, %s offline."
--#TYPE   "Array Manager Event: Array Disk offline"
--#SUMMARY  "%s, %s offline."
--#CATEGORY "Status Events"
--#ARGUMENTS { 0, 1 }
--#SEVERITY MINOR
--#STATE   DEGRADED
--#STATUS  MANDATORY
			::= 502
		arrayDiskDegraded TRAP-TYPE
			ENTERPRISE aryMgrEvts
			VARIABLES { controllerNameEv, arrayDiskNameEv }
			DESCRIPTION
				"%s, %s degraded."
--#TYPE   "Array Manager Event: Array Disk degraded"
--#SUMMARY  "%s, %s degraded."
--#CATEGORY "Status Events"
--#ARGUMENTS { 0, 1 }
--#SEVERITY MINOR
--#STATE   DEGRADED
--#STATUS  MANDATORY
			::= 503
		arrayDiskInserted TRAP-TYPE
			ENTERPRISE aryMgrEvts
			VARIABLES { controllerNameEv, arrayDiskNameEv }
			DESCRIPTION
				"%s, %s inserted."
--#TYPE   "Array Manager Event: Array Disk inserted"
--#SUMMARY  "%s, %s inserted."
--#CATEGORY "Status Events"
--#ARGUMENTS { 0, 1 }
--#SEVERITY INFORMATIONAL
--#STATE   OPERATIONAL
--#STATUS  MANDATORY
			::= 504
		virtualDiskCreated TRAP-TYPE
			ENTERPRISE aryMgrEvts
			VARIABLES { controllerNameEv, virtualDiskNameEv }
			DESCRIPTION
				"%s, virtual disk (%s) created."
--#TYPE   "Array Manager Event: Virtual Disk created"
--#SUMMARY  "%s, virtual disk (%s) created."
--#CATEGORY "Status Events"
--#ARGUMENTS { 0, 1 }
--#SEVERITY INFORMATIONAL
--#STATE   OPERATIONAL
--#STATUS  MANDATORY
			::= 505
		virtualDiskDeleted TRAP-TYPE
			ENTERPRISE aryMgrEvts
			VARIABLES { controllerNameEv, virtualDiskNameEv }
			DESCRIPTION
				"%s, virtual disk (%s) deleted."
--#TYPE   "Array Manager Event: Virtual Disk deleted"
--#SUMMARY  "%s, virtual disk (%s) deleted."
--#CATEGORY "Status Events"
--#ARGUMENTS { 0, 1 }
--#SEVERITY MINOR
--#STATE   FAILED
--#STATUS  MANDATORY
			::= 506
		virtualDiskConfigChanged TRAP-TYPE
			ENTERPRISE aryMgrEvts
			VARIABLES { controllerNameEv, virtualDiskNameEv, oldVDConfigEv, newVDConfigEv }
			DESCRIPTION
				"%s, virtual disk (%s) configuration changed from %s to %s"
--#TYPE   "Array Manager Event: Virtual Disk created"
--#SUMMARY  "%s, virtual disk (%s) configuration changed from %s to %s."
--#CATEGORY "Status Events"
--#ARGUMENTS { 0, 1, 2, 3 }
--#SEVERITY INFORMATIONAL
--#STATE   OPERATIONAL
--#STATUS  MANDATORY
			::= 507
		virtualDiskFailed TRAP-TYPE
			ENTERPRISE aryMgrEvts
			VARIABLES { controllerNameEv, virtualDiskNameEv }
			DESCRIPTION
				"%s, virtual disk (%s) failed."
--#TYPE   "Array Manager Event: Virtual Disk failed"
--#SUMMARY  "%s, virtual disk (%s) failed."
--#CATEGORY "Error Events"
--#ARGUMENTS { 0, 1 }
--#SEVERITY CRITICAL
--#STATE   FAILED
--#STATUS  MANDATORY
			::= 508
		virtualDiskDegraded TRAP-TYPE
			ENTERPRISE aryMgrEvts
			VARIABLES { controllerNameEv, virtualDiskNameEv }
			DESCRIPTION
				"%s, virtual disk (%s) degraded."
--#TYPE   "Array Manager Event: Virtual Disk degraded"
--#SUMMARY  "%s, virtual disk (%s) degraded."
--#CATEGORY "Status Events"
--#ARGUMENTS { 0, 1 }
--#SEVERITY MINOR
--#STATE   DEGRADED
--#STATUS  MANDATORY
			::= 509
		vdFailedRedundancy TRAP-TYPE
			ENTERPRISE aryMgrEvts
			VARIABLES { controllerNameEv, virtualDiskNameEv }
			DESCRIPTION
				"%s, virtual disk (%s) is no longer redundant."
--#TYPE   "Array Manager Event: Virtual Disk failed redundancy"
--#SUMMARY  "%s, virtual disk (%s) is no longer redundant."
--#CATEGORY "Status Events"
--#ARGUMENTS { 0, 1 }
--#SEVERITY MINOR
--#STATE   DEGRADED
--#STATUS  MANDATORY
			::= 510
		checkConsistencyStarted TRAP-TYPE
			ENTERPRISE aryMgrEvts
			VARIABLES { controllerNameEv, virtualDiskNameEv }
			DESCRIPTION
				"%s, virtual disk (%s) check consistency started."
--#TYPE   "Array Manager Event: Virtual Disk check consistency started"
--#SUMMARY  "%s, virtual disk (%s) check consistency started."
--#CATEGORY "Status Events"
--#ARGUMENTS { 0, 1 }
--#SEVERITY INFORMATIONAL
--#STATE   OPERATIONAL
--#STATUS  MANDATORY
			::= 520
		vdFormatStarted TRAP-TYPE
			ENTERPRISE aryMgrEvts
			VARIABLES { controllerNameEv, virtualDiskNameEv }
			DESCRIPTION
				"%s, virtual disk (%s) format started."
--#TYPE   "Array Manager Event: Virtual Disk format started"
--#SUMMARY  "%s, virtual disk (%s) format started."
--#CATEGORY "Status Events"
--#ARGUMENTS { 0, 1 }
--#SEVERITY INFORMATIONAL
--#STATE   OPERATIONAL
--#STATUS  MANDATORY
			::= 521
		adFormatStarted TRAP-TYPE
			ENTERPRISE aryMgrEvts
			VARIABLES { controllerNameEv, arrayDiskNameEv }
			DESCRIPTION
				"%s, %s format started."
--#TYPE   "Array Manager Event: Array Disk format started"
--#SUMMARY  "%s, %s format started."
--#CATEGORY "Status Events"
--#ARGUMENTS { 0, 1 }
--#SEVERITY INFORMATIONAL
--#STATE   OPERATIONAL
--#STATUS  MANDATORY
			::= 522
		vdInitializeStarted TRAP-TYPE
			ENTERPRISE aryMgrEvts
			VARIABLES { controllerNameEv, virtualDiskNameEv }
			DESCRIPTION
				"%s, virtual disk (%s) initialization started."
--#TYPE   "Array Manager Event: Virtual Disk initialization started"
--#SUMMARY  "%s, virtual disk (%s) initialization started."
--#CATEGORY "Status Events"
--#ARGUMENTS { 0, 1 }
--#SEVERITY INFORMATIONAL
--#STATE   OPERATIONAL
--#STATUS  MANDATORY
			::= 523
		adInitializeStarted TRAP-TYPE
			ENTERPRISE aryMgrEvts
			VARIABLES { controllerNameEv, arrayDiskNameEv }
			DESCRIPTION
				"%s, %s initialize started."
--#TYPE   "Array Manager Event: Array Disk initialize started"
--#SUMMARY  "%s, %s initialize started."
--#CATEGORY "Status Events"
--#ARGUMENTS { 0, 1 }
--#SEVERITY INFORMATIONAL
--#STATE   OPERATIONAL
--#STATUS  MANDATORY
			::= 524
		vdReconfigStarted TRAP-TYPE
			ENTERPRISE aryMgrEvts
			VARIABLES { controllerNameEv, virtualDiskNameEv, oldVDConfigEv, newVDConfigEv }
			DESCRIPTION
				"%s, virtual disk (%s) reconfiguration from
				%s stripe size to %s stripe size started."
--#TYPE   "Array Manager Event: Virtual Disk Reconfiguration started"
--#SUMMARY  "%s, virtual disk (%s) reconfiguration from %s stripe size to %s stripe size started."
--#CATEGORY "Status Events"
--#ARGUMENTS { 0, 1, 2, 3 }
--#SEVERITY INFORMATIONAL
--#STATE   OPERATIONAL
--#STATUS  MANDATORY
			::= 525
		vdRebuildStarted TRAP-TYPE
			ENTERPRISE aryMgrEvts
			VARIABLES { controllerNameEv, virtualDiskNameEv }
			DESCRIPTION
				"%s, virtual disk (%s) rebuild started."
--#TYPE   "Array Manager Event: Virtual Disk rebuild started"
--#SUMMARY  "%s, virtual disk (%s) rebuild started."
--#CATEGORY "Status Events"
--#ARGUMENTS { 0, 1 }
--#SEVERITY INFORMATIONAL
--#STATE   OPERATIONAL
--#STATUS  MANDATORY
			::= 526
		adRebuildStarted TRAP-TYPE
			ENTERPRISE aryMgrEvts
			VARIABLES { controllerNameEv, arrayDiskNameEv }
			DESCRIPTION
				"%s, %s rebuild started."
--#TYPE   "Array Manager Event: Array Disk rebuild started"
--#SUMMARY  "%s, %s rebuild started."
--#CATEGORY "Status Events"
--#ARGUMENTS { 0, 1 }
--#SEVERITY INFORMATIONAL
--#STATE   OPERATIONAL
--#STATUS  MANDATORY
			::= 527
		adDiagStarted TRAP-TYPE
			ENTERPRISE aryMgrEvts
			VARIABLES { controllerNameEv, arrayDiskNameEv }
			DESCRIPTION
				"%s, %s diagnostics started."
--#TYPE   "Array Manager Event: Array Disk diagnostics started"
--#SUMMARY  "%s, %s diagnostics started."
--#CATEGORY "Status Events"
--#ARGUMENTS { 0, 1 }
--#SEVERITY INFORMATIONAL
--#STATE   OPERATIONAL
--#STATUS  MANDATORY
			::= 528
		checkConsistencyCancelled TRAP-TYPE
			ENTERPRISE aryMgrEvts
			VARIABLES { controllerNameEv, virtualDiskNameEv }
			DESCRIPTION
				"%s, virtual disk (%s) consistency check cancelled."
--#TYPE   "Array Manager Event: Virtual Disk check consistency cancelled"
--#SUMMARY  "%s, virtual disk (%s) consistency check cancelled."
--#CATEGORY "Status Events"
--#ARGUMENTS { 0, 1 }
--#SEVERITY MINOR
--#STATE   OPERATIONAL
--#STATUS  MANDATORY
			::= 529
		vdFormatCancelled TRAP-TYPE
			ENTERPRISE aryMgrEvts
			VARIABLES { controllerNameEv, virtualDiskNameEv }
			DESCRIPTION
				"%s, virtual disk (%s) format cancelled."
--#TYPE   "Array Manager Event: Virtual Disk format cancelled"
--#SUMMARY  "%s, virtual disk (%s) format cancelled."
--#CATEGORY "Status Events"
--#ARGUMENTS { 0, 1 }
--#SEVERITY MINOR
--#STATE   OPERATIONAL
--#STATUS  MANDATORY
			::= 530
		adFormatCancelled TRAP-TYPE
			ENTERPRISE aryMgrEvts
			VARIABLES { controllerNameEv, arrayDiskNameEv }
			DESCRIPTION
				"%s, %s format cancelled."
--#TYPE   "Array Manager Event: Array Disk format cancelled"
--#SUMMARY  "%s, %s format cancelled."
--#CATEGORY "Status Events"
--#ARGUMENTS { 0, 1 }
--#SEVERITY MINOR
--#STATE   OPERATIONAL
--#STATUS  MANDATORY
			::= 531
		vdInitializeCancelled TRAP-TYPE
			ENTERPRISE aryMgrEvts
			VARIABLES { controllerNameEv, virtualDiskNameEv }
			DESCRIPTION
				"%s, virtual disk (%s) initialization cancelled."
--#TYPE   "Array Manager Event: Virtual Disk initialization cancelled"
--#SUMMARY  "%s, virtual disk (%s) initialization cancelled."
--#CATEGORY "Status Events"
--#ARGUMENTS { 0, 1 }
--#SEVERITY MINOR
--#STATE   OPERATIONAL
--#STATUS  MANDATORY
			::= 532
		adInitializeCancelled TRAP-TYPE
			ENTERPRISE aryMgrEvts
			VARIABLES { controllerNameEv, arrayDiskNameEv }
			DESCRIPTION
				"%s, %s initialize cancelled."
--#TYPE   "Array Manager Event: Array Disk initialize cancelled"
--#SUMMARY  "%s, virtual disk (%s) initialization cancelled."
--#CATEGORY "Status Events"
--#ARGUMENTS { 0, 1 }
--#SEVERITY MINOR
--#STATE   OPERATIONAL
--#STATUS  MANDATORY
			::= 533
		vdReconfigCancelled TRAP-TYPE
			ENTERPRISE aryMgrEvts
			VARIABLES { controllerNameEv, virtualDiskNameEv }
			DESCRIPTION
				"%s, virtual disk (%s) reconfiguration cancelled."
--#TYPE   "Array Manager Event: Virtual Disk Reconfiguration cancelled"
--#SUMMARY  "%s, virtual disk (%s) reconfiguration cancelled."
--#CATEGORY "Status Events"
--#ARGUMENTS { 0, 1 }
--#SEVERITY MINOR
--#STATE   OPERATIONAL
--#STATUS  MANDATORY
			::= 534
		vdRebuildCancelled TRAP-TYPE
			ENTERPRISE aryMgrEvts
			VARIABLES { controllerNameEv, virtualDiskNameEv }
			DESCRIPTION
				"%s, virtual disk (%s) rebuild cancelled."
--#TYPE   "Array Manager Event: Virtual Disk rebuild cancelled"
--#SUMMARY  "%s, virtual disk (%s) rebuild cancelled."
--#CATEGORY "Status Events"
--#ARGUMENTS { 0, 1 }
--#SEVERITY MINOR
--#STATE   OPERATIONAL
--#STATUS  MANDATORY
			::= 535
		adRebuildCancelled TRAP-TYPE
			ENTERPRISE aryMgrEvts
			VARIABLES { controllerNameEv, arrayDiskNameEv }
			DESCRIPTION
				"%s, %s rebuild cancelled."
--#TYPE   "Array Manager Event: Array Disk rebuild cancelled"
--#SUMMARY  "%s, %s rebuild cancelled."
--#CATEGORY "Status Events"
--#ARGUMENTS { 0, 1 }
--#SEVERITY MINOR
--#STATE   OPERATIONAL
--#STATUS  MANDATORY
			::= 536
		adDiagCancelled TRAP-TYPE
			ENTERPRISE aryMgrEvts
			VARIABLES { controllerNameEv, arrayDiskNameEv }
			DESCRIPTION
				"%s, %s diagnostics cancelled."
--#TYPE   "Array Manager Event: Array Disk diagnostics cancelled"
--#SUMMARY  "%s, %s diagnostics cancelled."
--#CATEGORY "Status Events"
--#ARGUMENTS { 0, 1 }
--#SEVERITY MINOR
--#STATE   OPERATIONAL
--#STATUS  MANDATORY
			::= 537
		checkConsistencyFailed TRAP-TYPE
			ENTERPRISE aryMgrEvts
			VARIABLES { controllerNameEv, virtualDiskNameEv }
			DESCRIPTION
				"%s, virtual disk (%s) consistency check failed."
--#TYPE   "Array Manager Event: Virtual Disk check consistency failed"
--#SUMMARY  "%s, virtual disk (%s) consistency check failed."
--#CATEGORY "Error Events"
--#ARGUMENTS { 0, 1 }
--#SEVERITY CRITICAL
--#STATE   FAILED
--#STATUS  MANDATORY
			::= 538
		vdFormatFailed TRAP-TYPE
			ENTERPRISE aryMgrEvts
			VARIABLES { controllerNameEv, virtualDiskNameEv }
			DESCRIPTION
				"%s, virtual disk (%s) format failed."
--#TYPE   "Array Manager Event: Virtual Disk format failed"
--#SUMMARY  "%s, virtual disk (%s) format failed."
--#CATEGORY "Error Events"
--#ARGUMENTS { 0, 1 }
--#SEVERITY CRITICAL
--#STATE   FAILED
--#STATUS  MANDATORY
			::= 539
		adFormatFailed TRAP-TYPE
			ENTERPRISE aryMgrEvts
			VARIABLES { controllerNameEv, arrayDiskNameEv }
			DESCRIPTION
				"%s, %s format failed."
--#TYPE   "Array Manager Event: Array Disk format failed"
--#SUMMARY  "%s, %s format failed."
--#CATEGORY "Error Events"
--#ARGUMENTS { 0, 1 }
--#SEVERITY CRITICAL
--#STATE   FAILED
--#STATUS  MANDATORY
			::= 540
		vdInitializeFailed TRAP-TYPE
			ENTERPRISE aryMgrEvts
			VARIABLES { controllerNameEv, virtualDiskNameEv }
			DESCRIPTION
				"%s, virtual disk (%s) initialization failed."
--#TYPE   "Array Manager Event: Virtual Disk initialization Failed"
--#SUMMARY  "%s, virtual disk (%s) initialization failed."
--#CATEGORY "Error Events"
--#ARGUMENTS { 0, 1 }
--#SEVERITY CRITICAL
--#STATE   FAILED
--#STATUS  MANDATORY
			::= 541
		adInitializeFailed TRAP-TYPE
			ENTERPRISE aryMgrEvts
			VARIABLES { controllerNameEv, arrayDiskNameEv }
			DESCRIPTION
				"%s, %s initialize failed."
--#TYPE   "Array Manager Event: Array Disk initialize failed"
--#SUMMARY  "%s, %s initialize failed."
--#CATEGORY "Error Events"
--#ARGUMENTS { 0, 1 }
--#SEVERITY CRITICAL
--#STATE   FAILED
--#STATUS  MANDATORY
			::= 542
		vdReconfigFailed TRAP-TYPE
			ENTERPRISE aryMgrEvts
			VARIABLES { controllerNameEv, virtualDiskNameEv }
			DESCRIPTION
				"%s, virtual disk (%s) reconfiguration failed."
--#TYPE   "Array Manager Event: Virtual Disk Reconfiguration failed"
--#SUMMARY  "%s, virtual disk (%s) reconfiguration failed."
--#CATEGORY "Error Events"
--#ARGUMENTS { 0, 1 }
--#SEVERITY CRITICAL
--#STATE   FAILED
--#STATUS  MANDATORY
			::= 543
		vdRebuildFailed TRAP-TYPE
			ENTERPRISE aryMgrEvts
			VARIABLES { controllerNameEv, virtualDiskNameEv }
			DESCRIPTION
				"%s, virtual disk (%s) rebuild failed."
--#TYPE   "Array Manager Event: Virtual Disk rebuild failed"
--#SUMMARY  "%s, virtual disk (%s) rebuild failed."
--#CATEGORY "Error Events"
--#ARGUMENTS { 0, 1 }
--#SEVERITY CRITICAL
--#STATE   FAILED
--#STATUS  MANDATORY
			::= 544
		adRebuildFailed TRAP-TYPE
			ENTERPRISE aryMgrEvts
			VARIABLES { controllerNameEv, arrayDiskNameEv }
			DESCRIPTION
				"%s, %s rebuild failed."
--#TYPE   "Array Manager Event: Array Disk rebuild failed"
--#SUMMARY  "%s, %s rebuild failed."
--#CATEGORY "Error Events"
--#ARGUMENTS { 0, 1 }
--#SEVERITY CRITICAL
--#STATE   FAILED
--#STATUS  MANDATORY
			::= 545
		adDiagFailed TRAP-TYPE
			ENTERPRISE aryMgrEvts
			VARIABLES { controllerNameEv, arrayDiskNameEv }
			DESCRIPTION
				"%s, %s diagnostics failed."
--#TYPE    "Array Manager Event: Array Disk diagnostics failed"
--#SUMMARY  "%s, %s diagnostics failed."
--#CATEGORY "Error Events"
--#ARGUMENTS { 0, 1 }
--#SEVERITY CRITICAL
--#STATE   FAILED
--#STATUS  MANDATORY
			::= 546
		checkConsistencyCompleted TRAP-TYPE
			ENTERPRISE aryMgrEvts
			VARIABLES { controllerNameEv, virtualDiskNameEv }
			DESCRIPTION
				"%s, virtual disk (%s) consistency check completed."
--#TYPE   "Array Manager Event: Virtual Disk check consistency completed"
--#SUMMARY  "%s, virtual disk (%s) consistency check completed."
--#CATEGORY "Status Events"
--#ARGUMENTS { 0, 1 }
--#SEVERITY INFORMATIONAL
--#STATE   OPERATIONAL
--#STATUS  MANDATORY
			::= 547
		vdFormatCompleted TRAP-TYPE
			ENTERPRISE aryMgrEvts
			VARIABLES { controllerNameEv, virtualDiskNameEv }
			DESCRIPTION
				"%s, virtual disk (%s) format completed."
--#TYPE   "Array Manager Event: Virtual Disk format completed"
--#SUMMARY  "%s, virtual disk (%s) format completed."
--#CATEGORY "Status Events"
--#ARGUMENTS { 0, 1 }
--#SEVERITY INFORMATIONAL
--#STATE   OPERATIONAL
--#STATUS  MANDATORY
			::= 548
		adFormatCompleted TRAP-TYPE
			ENTERPRISE aryMgrEvts
			VARIABLES { controllerNameEv, arrayDiskNameEv }
			DESCRIPTION
				"%s, %s format completed."
--#TYPE   "Array Manager Event: Array Disk format completed"
--#SUMMARY  "%s, %s format completed."
--#CATEGORY "Status Events"
--#ARGUMENTS { 0, 1 }
--#SEVERITY INFORMATIONAL
--#STATE   OPERATIONAL
--#STATUS  MANDATORY
			::= 549
		vdInitializeCompleted TRAP-TYPE
			ENTERPRISE aryMgrEvts
			VARIABLES { controllerNameEv, virtualDiskNameEv }
			DESCRIPTION
				"%s, virtual disk (%s) initialization completed."
--#TYPE   "Array Manager Event: Virtual Disk initialization completed"
--#SUMMARY  "%s, virtual disk (%s) initialization completed."
--#CATEGORY "Status Events"
--#ARGUMENTS { 0, 1 }
--#SEVERITY INFORMATIONAL
--#STATE   OPERATIONAL
--#STATUS  MANDATORY
			::= 550
		adInitializeCompleted TRAP-TYPE
			ENTERPRISE aryMgrEvts
			VARIABLES { controllerNameEv, arrayDiskNameEv }
			DESCRIPTION
				"%s, %s initialize completed."
--#TYPE   "Array Manager Event: Array Disk initialize completed"
--#SUMMARY  "%s, %s initialize completed."
--#CATEGORY "Status Events"
--#ARGUMENTS { 0, 1 }
--#SEVERITY INFORMATIONAL
--#STATE   OPERATIONAL
--#STATUS  MANDATORY
			::= 551
		vdReconfigCompleted TRAP-TYPE
			ENTERPRISE aryMgrEvts
			VARIABLES { controllerNameEv, virtualDiskNameEv }
			DESCRIPTION
				"%s, virtual disk (%s) reconfiguration completed."
--#TYPE   "Array Manager Event: Virtual Disk Reconfiguration completed"
--#SUMMARY  "%s, virtual disk (%s) reconfiguration completed."
--#CATEGORY "Status Events"
--#ARGUMENTS { 0, 1 }
--#SEVERITY INFORMATIONAL
--#STATE   OPERATIONAL
--#STATUS  MANDATORY
			::= 552
		vdRebuildCompleted TRAP-TYPE
			ENTERPRISE aryMgrEvts
			VARIABLES { controllerNameEv, virtualDiskNameEv }
			DESCRIPTION
				"%s, virtual disk (%s) rebuild completed."
--#TYPE   "Array Manager Event: Virtual Disk rebuild completed"
--#SUMMARY  "%s, virtual disk (%s) rebuild completed."
--#CATEGORY "Status Events"
--#ARGUMENTS { 0, 1 }
--#SEVERITY INFORMATIONAL
--#STATE   OPERATIONAL
--#STATUS  MANDATORY
			::= 553
		adRebuildCompleted TRAP-TYPE
			ENTERPRISE aryMgrEvts
			VARIABLES { controllerNameEv, arrayDiskNameEv }
			DESCRIPTION
				"%s, %s rebuild completed."
--#TYPE   "Array Manager Event: Array Disk rebuild completed"
--#SUMMARY  "%s, %s rebuild completed."
--#CATEGORY "Status Events"
--#ARGUMENTS { 0, 1 }
--#SEVERITY INFORMATIONAL
--#STATE   OPERATIONAL
--#STATUS  MANDATORY
			::= 554
		adDiagCompleted TRAP-TYPE
			ENTERPRISE aryMgrEvts
			VARIABLES { controllerNameEv, arrayDiskNameEv }
			DESCRIPTION
				"%s, %s diagnostics completed."
--#TYPE   "Array Manager Event: Array Disk diagnostics completed"
--#SUMMARY  "%s, %s diagnostics completed."
--#CATEGORY "Status Events"
--#ARGUMENTS { 0, 1 }
--#SEVERITY INFORMATIONAL
--#STATE   OPERATIONAL
--#STATUS  MANDATORY
			::= 555
		percPredictiveFailure TRAP-TYPE
			ENTERPRISE aryMgrEvts
			VARIABLES { controllerNameEv, arrayDiskNameEv }
			DESCRIPTION
				"%s, %s reported predictive failure.
				If this disk is part of a redundant virtual disk, select the
				'Offline' option and then replace the disk. Then configure a hot
				spare and it will start the rebuild automatically. If this disk
				is a hot spare, select the 'Prepare to Remove' option and then
				replace the disk. If this disk is part of a non-redundant disk,
				you should back-up your data immediately. If the disk fails,
				you will not be able to recover the data."
--#TYPE   "Array Manager Event: Predictive Failure reported"
--#SUMMARY  "%s, %s reported predictive failure."
--#CATEGORY "Status Events"
--#ARGUMENTS { 0, 1 }
--#SEVERITY MINOR
--#STATE   OPERATIONAL
--#STATUS  MANDATORY
			::= 570
		percSCSISenseData TRAP-TYPE
			ENTERPRISE aryMgrEvts
			VARIABLES { controllerNameEv, arrayDiskNameEv }
			DESCRIPTION
				"%s, %s SCSI sense failure. If this disk is part of a redundant
				virtual disk, select the 'Offline' option and then replace the
				disk. Then configure a hot spare and it will start the rebuild
				automatically. If this disk is a hot spare, select the 'Prepare
				to Remove' option and then replace the disk. If this disk is
				part of a non-redundant disk, you should back-up your data
				immediately. If the disk fails, you will not be able to recover
				the data."
--#TYPE   "Array Manager Event: SCSI sense data"
--#SUMMARY  "%s, %s reported predictive failure."
--#CATEGORY "Status Events"
--#ARGUMENTS { 0, 1 }
--#SEVERITY MINOR
--#STATE   OPERATIONAL
--#STATUS  MANDATORY
			::= 571
		percPauseIO TRAP-TYPE
			ENTERPRISE aryMgrEvts
			VARIABLES { controllerNameEv, channelNumberEv, timeEv }
			DESCRIPTION
				"%s, Channel %s I/O paused, I/O will automatically
				resume after the allotted time (%d seconds)."
--#TYPE   "Array Manager Event: I/O paused"
--#SUMMARY  "%s, Channel %s I/O paused, I/O will automatically resume after the allotted time (%d seconds)."
--#CATEGORY "Status Events"
--#ARGUMENTS { 0, 1, 2 }
--#SEVERITY MINOR
--#STATE   OPERATIONAL
--#STATUS  MANDATORY
			::= 572
		percResumeIO TRAP-TYPE
			ENTERPRISE aryMgrEvts
			VARIABLES { controllerNameEv, channelNumberEv }
			DESCRIPTION
				"%s, Channel %s I/O resumed."
--#TYPE   "Array Manager Event: I/O resumed"
--#SUMMARY  "%s, Channel %s I/O resumed."
--#CATEGORY "Status Events"
--#ARGUMENTS { 0, 1 }
--#SEVERITY INFORMATIONAL
--#STATE   OPERATIONAL
--#STATUS  MANDATORY
			::= 573
		percHotSpareAssign TRAP-TYPE
			ENTERPRISE aryMgrEvts
			VARIABLES { controllerNameEv, arrayDiskNameEv }
			DESCRIPTION
				"%s, assigned %s as Hot Spare."
--#TYPE   "Array Manager Event: Hot spare assigned"
--#SUMMARY  "%s, assigned %s as Hot Spare."
--#CATEGORY "Status Events"
--#ARGUMENTS { 0, 1 }
--#SEVERITY INFORMATIONAL
--#STATE   OPERATIONAL
--#STATUS  MANDATORY
			::= 574
		percHotSpareUnAssign TRAP-TYPE
			ENTERPRISE aryMgrEvts
			VARIABLES { controllerNameEv, arrayDiskNameEv }
			DESCRIPTION
				"%s, unassigned %s as Hot Spare."
--#TYPE   "Array Manager Event: Hot spare unassigned"
--#SUMMARY  "%s, unassigned %s as Hot Spare."
--#CATEGORY "Status Events"
--#ARGUMENTS { 0, 1 }
--#SEVERITY INFORMATIONAL
--#STATE   OPERATIONAL
--#STATUS  MANDATORY
			::= 575
		cntrlBatteryNeedsReconditioning TRAP-TYPE
			ENTERPRISE aryMgrEvts
			VARIABLES { controllerNameEv }
			DESCRIPTION
				"%s battery needs reconditioning."
--#TYPE   "Array Manager Event: Perc 2 Battery needs reconditioning"
--#SUMMARY  "%s battery needs reconditioning."
--#CATEGORY "Status Events"
--#ARGUMENTS { 0 }
--#SEVERITY MINOR
--#STATE   OPERATIONAL
--#STATUS  MANDATORY
			::= 579
		cntrlBatteryLow TRAP-TYPE
			ENTERPRISE aryMgrEvts
			VARIABLES { controllerNameEv }
			DESCRIPTION
				"%s battery low."
--#TYPE   "Array Manager Event: Perc 2 Battery low"
--#SUMMARY  "%s battery low."
--#CATEGORY "Status Events"
--#ARGUMENTS { 0 }
--#SEVERITY MINOR
--#STATE   OPERATIONAL
--#STATUS  MANDATORY
			::= 580
		cntrlBatteryRecondition TRAP-TYPE
			ENTERPRISE aryMgrEvts
			VARIABLES { controllerNameEv }
			DESCRIPTION
				"%s battery is reconditioning."
--#TYPE   "Array Manager Event: Perc 2 Battery reconditioning"
--#SUMMARY  "%s battery is reconditioning."
--#CATEGORY "Status Events"
--#ARGUMENTS { 0 }
--#SEVERITY INFORMATIONAL
--#STATE   OPERATIONAL
--#STATUS  MANDATORY
			::= 581
		cntrlBatteryReconComplete TRAP-TYPE
			ENTERPRISE aryMgrEvts
			VARIABLES { controllerNameEv }
			DESCRIPTION
				"%s battery reconditioning completed."
--#TYPE   "Array Manager Event: Perc 2 Battery reconditioning completed"
--#SUMMARY  "%s battery reconditioning completed."
--#CATEGORY "Status Events"
--#ARGUMENTS { 0 }
--#SEVERITY INFORMATIONAL
--#STATE   OPERATIONAL
--#STATUS  MANDATORY
			::= 582
		cntrlPauseIO TRAP-TYPE
			ENTERPRISE aryMgrEvts
			VARIABLES { controllerNameEv }
			DESCRIPTION
				"%s I/O paused, I/O will automatically resume after the allotted time."
--#TYPE   "Array Manager Event: Pause I/O"
--#SUMMARY  "%s I/O paused, I/O will automatically resume after the allotted time."
--#CATEGORY "Status Events"
--#ARGUMENTS { 0 }
--#SEVERITY MINOR
--#STATE   OPERATIONAL
--#STATUS  MANDATORY
			::= 583
		cntrlResumeIO TRAP-TYPE
			ENTERPRISE aryMgrEvts
			VARIABLES { controllerNameEv }
			DESCRIPTION
				"%s I/O resumed."
--#TYPE   "Array Manager Event: Resume I/O"
--#SUMMARY  "%s I/O resumed."
--#CATEGORY "Status Events"
--#ARGUMENTS { 0 }
--#SEVERITY INFORMATIONAL
--#STATE   OPERATIONAL
--#STATUS  MANDATORY
			::= 584
		perc2SmartFPTExceeded TRAP-TYPE
			ENTERPRISE aryMgrEvts
			VARIABLES { controllerNameEv, arrayDiskNameEv }
			DESCRIPTION
				"%s SMART:FPT_EXCEEDED on %s."
--#TYPE   "Array Manager Event: Smart FPT Exceeded"
--#SUMMARY  "%s SMART:FPT_EXCEEDED on %s."
--#CATEGORY "Status Events"
--#ARGUMENTS { 0, 1 }
--#SEVERITY MINOR
--#STATE   OPERATIONAL
--#STATUS  MANDATORY
			::= 585
		perc2SmartConfigChange TRAP-TYPE
			ENTERPRISE aryMgrEvts
			VARIABLES { controllerNameEv, arrayDiskNameEv }
			DESCRIPTION
				"%s SMART configuration change on %s."
--#TYPE   "Array Manager Event: Smart Config Change"
--#SUMMARY  "%s SMART configuration change on %s."
--#CATEGORY "Status Events"
--#ARGUMENTS { 0, 1 }
--#SEVERITY MINOR
--#STATE   OPERATIONAL
--#STATUS  MANDATORY
			::= 586
		perc2SmartWarning TRAP-TYPE
			ENTERPRISE aryMgrEvts
			VARIABLES { controllerNameEv, arrayDiskNameEv }
			DESCRIPTION
				"%s SMART warning on %s."
--#TYPE   "Array Manager Event: Smart Warning"
--#SUMMARY  "%s SMART warning on %s."
--#CATEGORY "Status Events"
--#ARGUMENTS { 0, 1 }
--#SEVERITY MINOR
--#STATE   OPERATIONAL
--#STATUS  MANDATORY
			::= 587
		perc2SmartWarningTemp TRAP-TYPE
			ENTERPRISE aryMgrEvts
			VARIABLES { controllerNameEv, arrayDiskNameEv }
			DESCRIPTION
				"%s SMART warning temperature on %s."
--#TYPE   "Array Manager Event: Smart warning temperature"
--#SUMMARY  "%s SMART warning temperature on %s."
--#CATEGORY "Status Events"
--#ARGUMENTS { 0, 1 }
--#SEVERITY MINOR
--#STATE   OPERATIONAL
--#STATUS  MANDATORY
			::= 588
		perc2SmartWarningDegraded TRAP-TYPE
			ENTERPRISE aryMgrEvts
			VARIABLES { controllerNameEv, arrayDiskNameEv }
			DESCRIPTION
				"%s SMART warning degraded on %s."
--#TYPE   "Array Manager Event: Smart warning degraded"
--#SUMMARY  "%s SMART warning degraded on %s."
--#CATEGORY "Status Events"
--#ARGUMENTS { 0, 1 }
--#SEVERITY MINOR
--#STATE   OPERATIONAL
--#STATUS  MANDATORY
			::= 589
		perc2SmartFPTExceededTest TRAP-TYPE
			ENTERPRISE aryMgrEvts
			VARIABLES { controllerNameEv, arrayDiskNameEv }
			DESCRIPTION
				"%s, On %s the failure prediction threshold exceeded due to test-No action needed."
--#TYPE   "Array Manager Event: Smart Config Change"
--#SUMMARY  "%s, On %s the failure prediction threshold exceeded due to test-No action needed."
--#CATEGORY "Status Events"
--#ARGUMENTS { 0, 1 }
--#SEVERITY MINOR
--#STATE   OPERATIONAL
--#STATUS  MANDATORY
			::= 590
		enclosureAlertTempWarnMax TRAP-TYPE
			ENTERPRISE aryMgrEvts
			VARIABLES { enclosureNameEv, unitNameEv }
			DESCRIPTION
				"%s, %s has exceded the maximum warning threshold."
--#TYPE   "Array Manager Event: Temperature exceeded the maximum warning threshold. "
--#SUMMARY  "%s, %s has exceded the maximum warning threshold."
--#CATEGORY "Status Events"
--#ARGUMENTS { 0, 1 }
--#SEVERITY MINOR
--#STATE   OPERATIONAL
--#STATUS  MANDATORY
			::= 591
		enclosureAlertTempWarnMin TRAP-TYPE
			ENTERPRISE aryMgrEvts
			VARIABLES { enclosureNameEv, unitNameEv }
			DESCRIPTION
				"%s, %s has dropped below the minimum warning threshold."
--#TYPE   "Array Manager Event: Temperature dropped below the minimum warning threshold. "
--#SUMMARY  "%s, %s has dropped below the minimum warning threshold."
--#CATEGORY "Status Events"
--#ARGUMENTS { 0, 1 }
--#SEVERITY MINOR
--#STATE   OPERATIONAL
--#STATUS  MANDATORY
			::= 592
		enclosureAlertTempErrMax TRAP-TYPE
			ENTERPRISE aryMgrEvts
			VARIABLES { enclosureNameEv, unitNameEv }
			DESCRIPTION
				"%s, %s has exceded the maximum error threshold."
--#TYPE   "Array Manager Event: Temperature exceeded the maximum error threshold. "
--#SUMMARY  "%s, %s has exceded the maximum error threshold."
--#CATEGORY "Error Events"
--#ARGUMENTS { 0, 1 }
--#SEVERITY CRITICAL
--#STATE   OPERATIONAL
--#STATUS  MANDATORY
			::= 593
		enclosureAlertTempErrMin TRAP-TYPE
			ENTERPRISE aryMgrEvts
			VARIABLES { enclosureNameEv, unitNameEv }
			DESCRIPTION
				"%s, %s has dropped below the minimum error threshold."
--#TYPE   "Array Manager Event: Temperature dropped below the minimum error threshold. "
--#SUMMARY  "%s, %s has dropped below the minimum error threshold."
--#CATEGORY "Error Events"
--#ARGUMENTS { 0, 1 }
--#SEVERITY CRITICAL
--#STATE   OPERATIONAL
--#STATUS  MANDATORY
			::= 594
		enclosureGenericFailed TRAP-TYPE
			ENTERPRISE aryMgrEvts
			VARIABLES { enclosureNameEv, unitNameEv }
			DESCRIPTION
				"%s, %s failed."
--#TYPE   "Array Manager Event: Enclosure failed. "
--#SUMMARY  "%s, %s failed."
--#CATEGORY "Error Events"
--#ARGUMENTS { 0, 1 }
--#SEVERITY CRITICAL
--#STATE   OPERATIONAL
--#STATUS  MANDATORY
			::= 595
		enclosureGenericOffline TRAP-TYPE
			ENTERPRISE aryMgrEvts
			VARIABLES { enclosureNameEv, unitNameEv }
			DESCRIPTION
				"%s, %s is offline."
--#TYPE   "Array Manager Event: Enclosure is offline. "
--#SUMMARY  "%s, %s is offline."
--#CATEGORY "Status Events"
--#ARGUMENTS { 0, 1 }
--#SEVERITY MINOR
--#STATE   OPERATIONAL
--#STATUS  MANDATORY
			::= 596
		enclosureGenericUnknown TRAP-TYPE
			ENTERPRISE aryMgrEvts
			VARIABLES { enclosureNameEv, unitNameEv }
			DESCRIPTION
				"%s, %s is in an unknown state."
--#TYPE   "Array Manager Event: Enclosure is in an unknown state. "
--#SUMMARY  "%s, %s is in an unknown state."
--#CATEGORY "Error Events"
--#ARGUMENTS { 0, 1 }
--#SEVERITY CRITICAL
--#STATE   OPERATIONAL
--#STATUS  MANDATORY
			::= 597
		enclosureGenericWarning TRAP-TYPE
			ENTERPRISE aryMgrEvts
			VARIABLES { enclosureNameEv, unitNameEv }
			DESCRIPTION
				"%s, %s is in a warning state."
--#TYPE   "Array Manager Event: Enclosure is in a warning state. "
--#SUMMARY  "%s, %s is in a warning state."
--#CATEGORY "Status Events"
--#ARGUMENTS { 0, 1 }
--#SEVERITY MINOR
--#STATE   OPERATIONAL
--#STATUS  MANDATORY
			::= 598
		enclosureGenericDegraded TRAP-TYPE
			ENTERPRISE aryMgrEvts
			VARIABLES { controllerNameEv, enclosureUnitNamesEv }
			DESCRIPTION
				"%s, %s is degraded."
--#TYPE   "Array Manager Event: Enclosure is in a degraded state. "
--#SUMMARY  "%s, %s is degraded."
--#CATEGORY "Error Events"
--#ARGUMENTS { 0, 1 }
--#SEVERITY MINOR
--#STATE   OPERATIONAL
--#STATUS  MANDATORY
			::= 600
		alertShutdownEnclosure TRAP-TYPE
			ENTERPRISE aryMgrEvts
			VARIABLES { controllerNameEv, enclosureNameEv }
			DESCRIPTION
				"%s, %s Shutting down."
--#TYPE   "Array Manager Event: Enclosure is shutting down. "
--#SUMMARY  "%s, %s Shutting down."
--#CATEGORY "Error Events"
--#ARGUMENTS { 0, 1 }
--#SEVERITY CRITICAL
--#STATE   OPERATIONAL
--#STATUS  MANDATORY
			::= 602
		alertShutdownServer TRAP-TYPE
			ENTERPRISE aryMgrEvts
			VARIABLES { controllerNameEv, enclosureNameEv }
			DESCRIPTION
				"%s, %s Shutting down the server."
--#TYPE   "Array Manager Event: Shutting down the server. "
--#SUMMARY  "%s, %s Shutting down the server."
--#CATEGORY "Error Events"
--#ARGUMENTS { 0, 1 }
--#SEVERITY CRITICAL
--#STATE   OPERATIONAL
--#STATUS  MANDATORY
			::= 603
		alertPausedCheckConsistency TRAP-TYPE
			ENTERPRISE aryMgrEvts
			VARIABLES { controllerNameEv, virtualDiskNameEv }
			DESCRIPTION
				"%s, Virtual Disk (%s) consistency check paused."
--#TYPE   "Array Manager Event: Consistency check paused. "
--#SUMMARY  "%s, Virtual Disk (%s) consistency check paused."
--#CATEGORY "Status Events"
--#ARGUMENTS { 0, 1 }
--#SEVERITY MINOR
--#STATE   OPERATIONAL
--#STATUS  MANDATORY
			::= 604
		alertResumedCheckConsistency TRAP-TYPE
			ENTERPRISE aryMgrEvts
			VARIABLES { controllerNameEv, virtualDiskNameEv }
			DESCRIPTION
				"%s, Virtual Disk (%s) consistency check resumed."
--#TYPE   "Array Manager Event: Consistency check resumed. "
--#SUMMARY  "%s, Virtual Disk (%s) consistency check resumed."
--#CATEGORY "Status Events"
--#ARGUMENTS { 0, 1 }
--#SEVERITY MINOR
--#STATE   OPERATIONAL
--#STATUS  MANDATORY
			::= 605
		alertVirtualDiskSplitMirror TRAP-TYPE
			ENTERPRISE aryMgrEvts
			VARIABLES { controllerNameEv, virtualDiskNameEv }
			DESCRIPTION
				"%s, Virtual Disk (%s) split mirror."
--#TYPE   "Array Manager Event: Virtual Disk split mirror."
--#SUMMARY  "%s, Virtual Disk (%s) split mirror."
--#CATEGORY "Status Events"
--#ARGUMENTS { 0, 1 }
--#SEVERITY INFORMATIONAL
--#STATE   OPERATIONAL
--#STATUS  MANDATORY
			::= 606
		alertVirtualDiskUnmirror TRAP-TYPE
			ENTERPRISE aryMgrEvts
			VARIABLES { controllerNameEv, virtualDiskNameEv }
			DESCRIPTION
				"%s, Virtual Disk (%s) unmirrored."
--#TYPE   "Array Manager Event: Virtual Disk unmirrored."
--#SUMMARY  "%s, Virtual Disk (%s) unmirrored."
--#CATEGORY "Status Events"
--#ARGUMENTS { 0, 1 }
--#SEVERITY INFORMATIONAL
--#STATE   OPERATIONAL
--#STATUS  MANDATORY
			::= 607
		alertRenameVirtualDisk TRAP-TYPE
			ENTERPRISE aryMgrEvts
			VARIABLES { controllerNameEv, virtualDiskNameEv, virtualDiskNameNewEv }
			DESCRIPTION
				"%s, %s renamed to %s."
--#TYPE   "Array Manager Event: Renamed Virtual Disk."
--#SUMMARY  "%s, %s renamed to %s."
--#CATEGORY "Status Events"
--#ARGUMENTS { 0, 1, 2 }
--#SEVERITY INFORMATIONAL
--#STATE   OPERATIONAL
--#STATUS  MANDATORY
			::= 608
		alertGenericReady TRAP-TYPE
			ENTERPRISE aryMgrEvts
			VARIABLES { controllerNameEv, device1NameEv }
			DESCRIPTION
				"%s, %s is in a ready state."
--#TYPE   "Array Manager Event: Device is in a ready state."
--#SUMMARY  "%s, %s is in a ready state."
--#CATEGORY "Status Events"
--#ARGUMENTS { 0, 1 }
--#SEVERITY INFORMATIONAL
--#STATE   OPERATIONAL
--#STATUS  MANDATORY
			::= 609
		alertCommTimeout TRAP-TYPE
			ENTERPRISE aryMgrEvts
			VARIABLES { controllerNameEv, device1NameEv }
			DESCRIPTION
				"%s, %s SES communication timeout."
--#TYPE   "Array Manager Event: Enclosure SES communication timeout."
--#SUMMARY  "%s, %s SES communication timeout."
--#CATEGORY "Status Events"
--#ARGUMENTS { 0, 1 }
--#SEVERITY MINOR
--#STATE   OPERATIONAL
--#STATUS  MANDATORY
			::= 610
		alertCommFailure TRAP-TYPE
			ENTERPRISE aryMgrEvts
			VARIABLES { controllerNameEv, device1NameEv }
			DESCRIPTION
				"%s, %s SES communication lost."
--#TYPE   "Array Manager Event: Enclosure SES communication failure."
--#SUMMARY  "%s, %s SES communication lost."
--#CATEGORY "Status Events"
--#ARGUMENTS { 0, 1 }
--#SEVERITY MINOR
--#STATE   OPERATIONAL
--#STATUS  MANDATORY
			::= 611
		alertCommRestored TRAP-TYPE
			ENTERPRISE aryMgrEvts
			VARIABLES { controllerNameEv, device1NameEv }
			DESCRIPTION
				"%s, %s SES communication restored."
--#TYPE   "Array Manager Event: Enclosure SES communication restored."
--#SUMMARY  "%s, %s SES communication restored."
--#CATEGORY "Status Events"
--#ARGUMENTS { 0, 1 }
--#SEVERITY INFORMATIONAL
--#STATE   OPERATIONAL
--#STATUS  MANDATORY
			::= 612
		genericEvent_DATABASE_UP TRAP-TYPE
			ENTERPRISE aryMgrEvts
			DESCRIPTION
				"Communication with the Array Manager database is now
				possible."
--#TYPE   "Array Manager Event: Array Manager Database UP"
--#SUMMARY  "Communication with the Array Manager database is now possible."
--#CATEGORY "Status Events"
--#ARGUMENTS { }
--#SEVERITY INFORMATIONAL
--#STATE   OPERATIONAL
--#STATUS  MANDATORY
			::= 650
		genericEvent_DATABASE_DOWN TRAP-TYPE
			ENTERPRISE aryMgrEvts
			DESCRIPTION
				"Communication with the Array Manager database is NOT
				possible."
--#TYPE   "Array Manager Event: Array Manager Database DOWN"
--#SUMMARY  "Communication with the Array Manager database is NOT possible."
--#CATEGORY "Status Events"
--#ARGUMENTS { }
--#SEVERITY INFORMATIONAL
--#STATE   OPERATIONAL
--#STATUS  MANDATORY
			::= 651
		alertMegalibTimeout TRAP-TYPE
			ENTERPRISE aryMgrEvts
			VARIABLES { controllerNameEv }
			DESCRIPTION
				"%s Array Manager has lost communication with this RAID controller and subsystem."
--#TYPE   "Array Manager Event: Array Manager has lost communication with this RAID controller and subsystem."
--#SUMMARY  "%s Array Manager has lost communication with this RAID controller and subsystem."
--#CATEGORY "Error Events"
--#ARGUMENTS { 0 }
--#SEVERITY CRITICAL
--#STATE   OPERATIONAL
--#STATUS  MANDATORY
			::= 668
		alertScsiSenseFormatFail TRAP-TYPE
			ENTERPRISE aryMgrEvts
			VARIABLES { controllerNameEv, arrayDiskNameEv, senseKeyEv, senseCodeEv, senseQualifierEv
				 }
			DESCRIPTION
				"%s, %s Sense Key = %s, Sense Code = %s, Sense Qualifier = %s A format
				unit operation was interrupted prior to completion."
--#TYPE   "Array Manager Event: Disk format corruption."
--#SUMMARY  "%s, %s Sense Key = %s, Sense Code = %s A format
-- unit operation was interrupted prior to completion."
--#CATEGORY "Status Events"
--#ARGUMENTS { 0, 1, 2, 3, 4 }
--#SEVERITY MINOR
--#STATE   OPERATIONAL
--#STATUS  MANDATORY
			::= 670
		alertScsiSenseSectorReassign TRAP-TYPE
			ENTERPRISE aryMgrEvts
			VARIABLES { controllerNameEv, arrayDiskNameEv, senseKeyEv, senseCodeEv, senseQualifierEv
				 }
			DESCRIPTION
				"%s, %s Sense Key = %s, Sense Code = %s, Sense Qualifier = %s
				If this disk is part of a non-redundant virtual disk, the data for this block cannot be recovered."
--#TYPE   "Array Manager Event: Disk sector reassigned. "
--#SUMMARY  "%s, %s Sense Key = %s, Sense Code = %s, Sense Qualifier = %s
-- If this disk is part of a non-redundant virtual disk, the data for this
-- block cannot be recovered."
--#CATEGORY "Status Events"
--#ARGUMENTS { 0, 1, 2, 3, 4 }
--#SEVERITY MINOR
--#STATE   OPERATIONAL
--#STATUS  MANDATORY
			::= 671
		alertEmmFwMismatch TRAP-TYPE
			ENTERPRISE aryMgrEvts
			VARIABLES { controllerNameEv, enclosureNameEv, eMMFWVersion0Ev, eMMFWVersion1Ev }
			DESCRIPTION
				"%s, %s EMMfirmware mismatch (%s / %s.)
				This is an unsupported configuration. Please download the
				firmware to this enclosure again to correct this condition."
--#TYPE   "Array Manager Event: EMM firmware mismatch."
--#SUMMARY  "%s, %s EMMfirmware mismatch (%s / %s.)
-- This is an unsupported configuration. Please download the
-- firmware to this enclosure again to correct this condition."
--#CATEGORY "Status Events"
--#ARGUMENTS { 0, 1, 2, 3, 4 }
--#SEVERITY MINOR
--#STATE   OPERATIONAL
--#STATUS  MANDATORY
			::= 672
		alertConserveCacheModeEnable TRAP-TYPE
			ENTERPRISE aryMgrEvts
			VARIABLES { controllerNameEv, enclosureNameEv }
			DESCRIPTION
				"%s, %s conservative cache mode enabled."
--#TYPE   "Array Manager Event: Conservative cache mode enabled."
--#SUMMARY  "%s, %s conservative cache mode enabled."
--#CATEGORY "Status Events"
--#ARGUMENTS { 0, 1 }
--#SEVERITY INFORMATIONAL
--#STATE   OPERATIONAL
--#STATUS  MANDATORY
			::= 673
		alertConserveCacheModeDisable TRAP-TYPE
			ENTERPRISE aryMgrEvts
			VARIABLES { controllerNameEv, enclosureNameEv }
			DESCRIPTION
				"%s, %s conservative cache mode disabled."
--#TYPE   "Array Manager Event: Conservative cache mode disabled."
--#SUMMARY  "%s, %s conservative cache mode disabled."
--#CATEGORY "Status Events"
--#ARGUMENTS { 0, 1 }
--#SEVERITY INFORMATIONAL
--#STATE   OPERATIONAL
--#STATUS  MANDATORY
			::= 674
		alertEnclosureFwDownload TRAP-TYPE
			ENTERPRISE aryMgrEvts
			VARIABLES { controllerNameEv, enclosureNameEv, eMMFWVersion0Ev }
			DESCRIPTION
				"%s, %s firmware version %s downloaded successfully."
--#TYPE   "Array Manager Event: Firmware downloaded successfully."
--#SUMMARY  "%s, %s firmware version %s downloaded successfully."
--#CATEGORY "Status Events"
--#ARGUMENTS { 0, 1, 2 }
--#SEVERITY INFORMATIONAL
--#STATE   OPERATIONAL
--#STATUS  MANDATORY
			::= 675
		alertEnclosureAlarmEnable TRAP-TYPE
			ENTERPRISE aryMgrEvts
			VARIABLES { controllerNameEv, enclosureNameEv }
			DESCRIPTION
				"%s, %s alarm enabled."
--#TYPE   "Array Manager Event: Enclosure alarm enabled."
--#SUMMARY  "%s, %s alarm enabled."
--#CATEGORY "Status Events"
--#ARGUMENTS { 0, 1 }
--#SEVERITY INFORMATIONAL
--#STATE   OPERATIONAL
--#STATUS  MANDATORY
			::= 676
		alertEnclosureAlarmDisable TRAP-TYPE
			ENTERPRISE aryMgrEvts
			VARIABLES { controllerNameEv, enclosureNameEv }
			DESCRIPTION
				"%s, %s alarm disabled."
--#TYPE   "Array Manager Event: Enclosure alarm disabled."
--#SUMMARY  "%s, %s alarm disabled."
--#CATEGORY "Status Events"
--#ARGUMENTS { 0, 1 }
--#SEVERITY INFORMATIONAL
--#STATE   OPERATIONAL
--#STATUS  MANDATORY
			::= 677
		alertControllerAlarmEnable TRAP-TYPE
			ENTERPRISE aryMgrEvts
			VARIABLES { controllerNameEv }
			DESCRIPTION
				"%s, %s alarm enabled."
--#TYPE   "Array Manager Event: Controller alarm enabled."
--#SUMMARY  "%s, %s alarm enabled."
--#CATEGORY "Status Events"
--#ARGUMENTS { 0 }
--#SEVERITY INFORMATIONAL
--#STATE   OPERATIONAL
--#STATUS  MANDATORY
			::= 678
		alertControllerAlarmDisable TRAP-TYPE
			ENTERPRISE aryMgrEvts
			VARIABLES { controllerNameEv }
			DESCRIPTION
				"%s, %s alarm disabled."
--#TYPE   "Array Manager Event: Controller alarm disabled."
--#SUMMARY  "%s, %s alarm disabled."
--#CATEGORY "Status Events"
--#ARGUMENTS { 0 }
--#SEVERITY INFORMATIONAL
--#STATE   OPERATIONAL
--#STATUS  MANDATORY
			::= 679
		alertControllerRebuildRate TRAP-TYPE
			ENTERPRISE aryMgrEvts
			VARIABLES { controllerNameEv, rebuildRateEv }
			DESCRIPTION
				"%s, rebuild rate changed to %s."
--#TYPE   "Array Manager Event: Rebuild rate changed."
--#SUMMARY  "%s, rebuild rate changed to %s."
--#CATEGORY "Status Events"
--#ARGUMENTS { 0, 1 }
--#SEVERITY INFORMATIONAL
--#STATE   OPERATIONAL
--#STATUS  MANDATORY
			::= 680
		alertArrayDiskForcedOnline TRAP-TYPE
			ENTERPRISE aryMgrEvts
			VARIABLES { controllerNameEv, arrayDiskNameEv }
			DESCRIPTION
				"%s, %s forced online."
--#TYPE   "Array Manager Event: Array disk forced online."
--#SUMMARY  "%s, %s forced online."
--#CATEGORY "Status Events"
--#ARGUMENTS { 0, 1 }
--#SEVERITY INFORMATIONAL
--#STATE   OPERATIONAL
--#STATUS  MANDATORY
			::= 681
		alertArrayDiskForcedOffline TRAP-TYPE
			ENTERPRISE aryMgrEvts
			VARIABLES { controllerNameEv, arrayDiskNameEv }
			DESCRIPTION
				"%s, %s forced offline."
--#TYPE   "Array Manager Event: Array disk forced offline."
--#SUMMARY  "%s, %s forced offline."
--#CATEGORY "Status Events"
--#ARGUMENTS { 0, 1 }
--#SEVERITY MINOR
--#STATE   OPERATIONAL
--#STATUS  MANDATORY
			::= 682
		alertTaskBGI TRAP-TYPE
			ENTERPRISE aryMgrEvts
			VARIABLES { controllerNameEv, virtualDiskNameEv }
			DESCRIPTION
				"%s, virtual disk %s background initialization started."
--#TYPE   "Array Manager Event: Background initialization started."
--#SUMMARY  "%s, virtual disk %s background initialization started."
--#CATEGORY "Status Events"
--#ARGUMENTS { 0, 1 }
--#SEVERITY INFORMATIONAL
--#STATE   OPERATIONAL
--#STATUS  MANDATORY
			::= 683
		alertCancelBGI TRAP-TYPE
			ENTERPRISE aryMgrEvts
			VARIABLES { controllerNameEv, virtualDiskNameEv }
			DESCRIPTION
				"%s, virtual disk %s background initialization cancelled."
--#TYPE   "Array Manager Event: Background initialization cancelled."
--#SUMMARY  "%s, virtual disk %s background initialization cancelled."
--#CATEGORY "Status Events"
--#ARGUMENTS { 0, 1 }
--#SEVERITY MINOR
--#STATE   OPERATIONAL
--#STATUS  MANDATORY
			::= 684
		alertFailBGI TRAP-TYPE
			ENTERPRISE aryMgrEvts
			VARIABLES { controllerNameEv, virtualDiskNameEv }
			DESCRIPTION
				"%s, virtual disk %s background initialization failed."
--#TYPE   "Array Manager Event: Background initialization failed."
--#SUMMARY  "%s, virtual disk %s background initialization failed."
--#CATEGORY "Error Events"
--#ARGUMENTS { 0, 1 }
--#SEVERITY CRITICAL
--#STATE   OPERATIONAL
--#STATUS  MANDATORY
			::= 685
		alertCompleteBGI TRAP-TYPE
			ENTERPRISE aryMgrEvts
			VARIABLES { controllerNameEv, virtualDiskNameEv }
			DESCRIPTION
				"%s, virtual disk %s background initialization completed."
--#TYPE   "Array Manager Event: Background initialization completed."
--#SUMMARY  "%s, virtual disk %s background initialization completed."
--#CATEGORY "Status Events"
--#ARGUMENTS { 0, 1 }
--#SEVERITY INFORMATIONAL
--#STATE   OPERATIONAL
--#STATUS  MANDATORY
			::= 686
		enclosureGenericNotInstalled TRAP-TYPE
			ENTERPRISE aryMgrEvts
			VARIABLES { controllerNameEv, enclosureUnitNamesEv }
			DESCRIPTION
				"%s, %s is not installed."
--#TYPE   "Array Manager Event: Enclosure component is not installed. "
--#SUMMARY  "%s, %s is not installed."
--#CATEGORY "Status Events"
--#ARGUMENTS { 0, 1 }
--#SEVERITY INFORMATIONAL
--#STATE   OPERATIONAL
--#STATUS  MANDATORY
			::= 687
		pv660fEvent_PHYSDEV_ONLINE TRAP-TYPE
			ENTERPRISE aryMgrEvts
			VARIABLES { controllerNameEv, channelNumberEv, targetIDEv }
			DESCRIPTION
				"A hard disk has been placed online."
--#SUMMARY  "[ctl: %d chn: %d tgt: %d :] A hard disk has been placed online."
--#CATEGORY "Status Events"
--#ARGUMENTS { 0, 1, 2 }
--#SEVERITY INFORMATIONAL
--#TIMEINDEX 4
--#STATE   OPERATIONAL
--#STATUS  MANDATORY
			::= 700
		pv660fEvent_PHYSDEV_HOTSPARE TRAP-TYPE
			ENTERPRISE aryMgrEvts
			VARIABLES { controllerNameEv, channelNumberEv, targetIDEv }
			DESCRIPTION
				"A hard disk added as hot spare."
--#SUMMARY  "[ctl: %d chn: %d tgt: %d :] A hard disk added as hot spare."
--#CATEGORY "IGNORE"
--#ARGUMENTS { 0, 1, 2 }
--#SEVERITY INFORMATIONAL
--#TIMEINDEX 4
--#STATE   OPERATIONAL
--#STATUS  OBSOLETE
			::= 701
		pv660fEvent_PHYSDEV_HARD_ERROR TRAP-TYPE
			ENTERPRISE aryMgrEvts
			VARIABLES { controllerNameEv, channelNumberEv, targetIDEv }
			DESCRIPTION
				"Hard disk error found."
--#SUMMARY  "[ctl: %d chn: %d tgt: %d :] Hard disk error found."
--#CATEGORY "Status Events"
--#ARGUMENTS { 0, 1, 2 }
--#SEVERITY MINOR
--#TIMEINDEX 4
--#STATE   OPERATIONAL
--#STATUS  MANDATORY
			::= 702
		pv660fEvent_PHYSDEV_PFA TRAP-TYPE
			ENTERPRISE aryMgrEvts
			VARIABLES { controllerNameEv, channelNumberEv, targetIDEv }
			DESCRIPTION
				"Hard disk PFA condition found, this disk may fail soon."
--#SUMMARY  "[ctl: %d chn: %d tgt: %d :] Hard disk PFA condition found, this disk may fail soon."
--#CATEGORY "Status Events"
--#ARGUMENTS { 0, 1, 2 }
--#SEVERITY MINOR
--#TIMEINDEX 4
--#STATE   OPERATIONAL
--#STATUS  MANDATORY
			::= 703
		pv660fEvent_PHYSDEV_AUTO_REBUILD_START TRAP-TYPE
			ENTERPRISE aryMgrEvts
			VARIABLES { controllerNameEv, channelNumberEv, targetIDEv }
			DESCRIPTION
				"An automatic rebuild has started."
--#SUMMARY  "[ctl: %d chn: %d tgt: %d :] An automatic rebuild has started."
--#CATEGORY "Status Events"
--#ARGUMENTS { 0, 1, 2 }
--#SEVERITY INFORMATIONAL
--#TIMEINDEX 4
--#STATE   OPERATIONAL
--#STATUS  MANDATORY
			::= 704
		pv660fEvent_PHYSDEV_MANUAL_REBUILD_START TRAP-TYPE
			ENTERPRISE aryMgrEvts
			VARIABLES { controllerNameEv, channelNumberEv, targetIDEv }
			DESCRIPTION
				"A rebuild has started."
--#SUMMARY  "[ctl: %d chn: %d tgt: %d :] A rebuild has started."
--#CATEGORY "Status Events"
--#ARGUMENTS {0, 1, 2}
--#SEVERITY INFORMATIONAL
--#TIMEINDEX 4
--#STATE   OPERATIONAL
--#STATUS  MANDATORY
			::= 705
		pv660fEvent_PHYSDEV_REBUILD_DONE TRAP-TYPE
			ENTERPRISE aryMgrEvts
			VARIABLES { controllerNameEv, channelNumberEv, targetIDEv }
			DESCRIPTION
				"Rebuild is over."
--#SUMMARY  "[ctl: %d chn: %d tgt: %d :] Rebuild is over."
--#CATEGORY "Status Events"
--#ARGUMENTS { 0, 1, 2 }
--#SEVERITY INFORMATIONAL
--#TIMEINDEX 4
--#STATE   OPERATIONAL
--#STATUS  MANDATORY
			::= 706
		pv660fEvent_PHYSDEV_REBUILD_CANCELED TRAP-TYPE
			ENTERPRISE aryMgrEvts
			VARIABLES { controllerNameEv, channelNumberEv, targetIDEv }
			DESCRIPTION
				"Rebuild is cancelled."
--#SUMMARY  "[ctl: %d chn: %d tgt: %d :] Rebuild is cancelled."
--#CATEGORY "Status Events"
--#ARGUMENTS { 0, 1, 2 }
--#SEVERITY MINOR
--#TIMEINDEX 4
--#STATE   OPERATIONAL
--#STATUS  MANDATORY
			::= 707
		pv660fEvent_PHYSDEV_REBUILD_ERROR TRAP-TYPE
			ENTERPRISE aryMgrEvts
			VARIABLES { controllerNameEv, channelNumberEv, targetIDEv }
			DESCRIPTION
				"Rebuild stopped with error."
--#SUMMARY  "[ctl: %d chn: %d tgt: %d :] Rebuild stopped with error."
--#CATEGORY "Error Events"
--#ARGUMENTS { 0, 1, 2 }
--#SEVERITY CRITICAL
--#TIMEINDEX 4
--#STATE   NONOPERATIONAL
--#STATUS  MANDATORY
			::= 708
		pv660fEvent_PHYSDEV_REBUILD_NEWDEV_FAILED TRAP-TYPE
			ENTERPRISE aryMgrEvts
			VARIABLES { controllerNameEv, channelNumberEv, targetIDEv }
			DESCRIPTION
				"Rebuild stopped with error. New device failed."
--#SUMMARY  "[ctl: %d chn: %d tgt: %d :] Rebuild stopped with error. New device failed."
--#CATEGORY "Error Events"
--#ARGUMENTS { 0, 1, 2 }
--#SEVERITY CRITICAL
--#TIMEINDEX 4
--#STATE   NONOPERATIONAL
--#STATUS  MANDATORY
			::= 709
		pv660fEvent_PHYSDEV_REBUILD_SYSDEV_FAILED TRAP-TYPE
			ENTERPRISE aryMgrEvts
			VARIABLES { controllerNameEv, channelNumberEv, targetIDEv }
			DESCRIPTION
				"Rebuild stopped because logical drive failed."
--#SUMMARY  "[ctl: %d chn: %d tgt: %d :] Rebuild stopped because logical drive failed."
--#CATEGORY "Error Events"
--#ARGUMENTS { 0, 1, 2 }
--#SEVERITY CRITICAL
--#TIMEINDEX 4
--#STATE   NONOPERATIONAL
--#STATUS  MANDATORY
			::= 710
		pv660fEvent_PHYSDEV_DEAD TRAP-TYPE
			ENTERPRISE aryMgrEvts
			VARIABLES { controllerNameEv, channelNumberEv, targetIDEv }
			DESCRIPTION
				"A hard disk has failed."
--#SUMMARY  "[ctl: %d chn: %d tgt: %d :] A hard disk has failed."
--#CATEGORY "Error Events"
--#ARGUMENTS { 0, 1, 2 }
--#SEVERITY MAJOR
--#TIMEINDEX 4
--#STATUS  MANDATORY
--#STATE   OPERATIONAL
			::= 711
		pv660fEvent_PHYSDEV_FOUND TRAP-TYPE
			ENTERPRISE aryMgrEvts
			VARIABLES { controllerNameEv, channelNumberEv, targetIDEv }
			DESCRIPTION
				"A new hard disk has been found."
--#SUMMARY  "[ctl: %d chn: %d tgt: %d :] A new hard disk has been found."
--#CATEGORY "Status Events"
--#ARGUMENTS { 0, 1, 2 }
--#SEVERITY INFORMATIONAL
--#TIMEINDEX 4
--#STATE   OPERATIONAL
--#STATUS  MANDATORY
			::= 712
		pv660fEvent_PHYSDEV_GONE TRAP-TYPE
			ENTERPRISE aryMgrEvts
			VARIABLES { controllerNameEv, channelNumberEv, targetIDEv }
			DESCRIPTION
				"A hard disk has been removed."
--#SUMMARY  "[ctl: %d chn: %d tgt: %d :] A hard disk has been removed."
--#CATEGORY "Status Events"
--#ARGUMENTS { 0, 1, 2 }
--#SEVERITY INFORMATIONAL
--#TIMEINDEX 4
--#STATE   OPERATIONAL
--#STATUS  MANDATORY
			::= 713
		pv660fEvent_PHYSDEV_UNCONFIGURED TRAP-TYPE
			ENTERPRISE aryMgrEvts
			VARIABLES { controllerNameEv, channelNumberEv, targetIDEv }
			DESCRIPTION
				"A previously configured disk is now available."
--#SUMMARY  "[ctl: %d chn: %d tgt: %d :] A previously configured disk is now available."
--#CATEGORY "IGNORE"
--#ARGUMENTS { 0, 1, 2 }
--#SEVERITY INFORMATIONAL
--#TIMEINDEX 4
--#STATE   OPERATIONAL
--#STATUS  OBSOLETE
			::= 714
		pv660fEvent_PHYSDEV_EXPANDCAPACITY_START TRAP-TYPE
			ENTERPRISE aryMgrEvts
			VARIABLES { controllerNameEv, channelNumberEv, targetIDEv }
			DESCRIPTION
				"Expand Capacity Started."
--#SUMMARY  "[ctl: %d chn: %d tgt: %d :] Expand Capacity Started."
--#CATEGORY "IGNORE"
--#ARGUMENTS { 0, 1, 2 }
--#SEVERITY INFORMATIONAL
--#TIMEINDEX 4
--#STATE   OPERATIONAL
--#STATUS  OBSOLETE
			::= 715
		pv660fEvent_PHYSDEV_EXPANDCAPACITY_DONE TRAP-TYPE
			ENTERPRISE aryMgrEvts
			VARIABLES { controllerNameEv, channelNumberEv, targetIDEv }
			DESCRIPTION
				"Expand Capacity Completed."
--#SUMMARY  "[ctl: %d chn: %d tgt: %d :] Expand Capacity Completed."
--#CATEGORY "IGNORE"
--#ARGUMENTS { 0, 1, 2 }
--#SEVERITY INFORMATIONAL
--#TIMEINDEX 4
--#STATE   OPERATIONAL
--#STATUS  OBSOLETE
			::= 716
		pv660fEvent_PHYSDEV_EXPANDCAPACITY_ERROR TRAP-TYPE
			ENTERPRISE aryMgrEvts
			VARIABLES { controllerNameEv, channelNumberEv, targetIDEv }
			DESCRIPTION
				"Expand Capacity Stopped with error."
--#SUMMARY  "[ctl: %d chn: %d tgt: %d :] Expand Capacity Stopped with error."
--#CATEGORY "IGNORE"
--#ARGUMENTS { 0, 1, 2 }
--#SEVERITY CRITICAL
--#TIMEINDEX 4
--#STATE   NONOPERATIONAL
--#STATUS  OBSOLETE
			::= 717
		pv660fEvent_PHYSDEV_COMMAND_TIMEOUT TRAP-TYPE
			ENTERPRISE aryMgrEvts
			VARIABLES { controllerNameEv, channelNumberEv, targetIDEv }
			DESCRIPTION
				"SCSI command timeout on hard device."
--#SUMMARY  "[ctl: %d chn: %d tgt: %d :] SCSI command timeout on hard device."
--#CATEGORY "Status Events"
--#ARGUMENTS { 0, 1, 2 }
--#SEVERITY MINOR
--#TIMEINDEX 4
--#STATE   OPERATIONAL
--#STATUS  MANDATORY
			::= 718
		pv660fEvent_PHYSDEV_COMMAND_ABORT TRAP-TYPE
			ENTERPRISE aryMgrEvts
			VARIABLES { controllerNameEv, channelNumberEv, targetIDEv }
			DESCRIPTION
				"SCSI command abort on hard disk."
--#SUMMARY  "[ctl: %d chn: %d tgt: %d :] SCSI command abort on hard disk."
--#CATEGORY "Status Events"
--#ARGUMENTS { 0, 1, 2 }
--#SEVERITY MINOR
--#TIMEINDEX 4
--#STATE   OPERATIONAL
--#STATUS  MANDATORY
			::= 719
		pv660fEvent_PHYSDEV_COMMAND_RETRIED TRAP-TYPE
			ENTERPRISE aryMgrEvts
			VARIABLES { controllerNameEv, channelNumberEv, targetIDEv }
			DESCRIPTION
				"SCSI command retried on hard disk."
--#SUMMARY  "[ctl: %d chn: %d tgt: %d :] SCSI command retried on hard disk."
--#CATEGORY "Status Events"
--#ARGUMENTS { 0, 1, 2 }
--#SEVERITY MINOR
--#TIMEINDEX 4
--#STATE   OPERATIONAL
--#STATUS  MANDATORY
			::= 720
		pv660fEvent_PHYSDEV_PARITY_ERROR TRAP-TYPE
			ENTERPRISE aryMgrEvts
			VARIABLES { controllerNameEv, channelNumberEv, targetIDEv }
			DESCRIPTION
				"Parity error found."
--#SUMMARY  "[ctl: %d chn: %d tgt: %d :] Parity error found."
--#CATEGORY "Status Events"
--#ARGUMENTS { 0, 1, 2 }
--#SEVERITY MINOR
--#TIMEINDEX 4
--#STATE   OPERATIONAL
--#STATUS  MANDATORY
			::= 721
		pv660fEvent_PHYSDEV_SOFT_ERROR TRAP-TYPE
			ENTERPRISE aryMgrEvts
			VARIABLES { controllerNameEv, channelNumberEv, targetIDEv }
			DESCRIPTION
				"Soft error found."
--#SUMMARY  "[ctl: %d chn: %d tgt: %d :] Soft error found."
--#CATEGORY "Status Events"
--#ARGUMENTS { 0, 1, 2 }
--#SEVERITY MINOR
--#TIMEINDEX 4
--#STATE   OPERATIONAL
--#STATUS  MANDATORY
			::= 722
		pv660fEvent_PHYSDEV_MISC_ERROR TRAP-TYPE
			ENTERPRISE aryMgrEvts
			VARIABLES { controllerNameEv, channelNumberEv, targetIDEv }
			DESCRIPTION
				"Misc error found."
--#SUMMARY  "[ctl: %d chn: %d tgt: %d :] Misc error found."
--#CATEGORY "Status Events"
--#ARGUMENTS { 0, 1, 2 }
--#SEVERITY MINOR
--#TIMEINDEX 4
--#STATE   OPERATIONAL
--#STATUS  MANDATORY
			::= 723
		pv660fEvent_PHYSDEV_RESET TRAP-TYPE
			ENTERPRISE aryMgrEvts
			VARIABLES { controllerNameEv, channelNumberEv, targetIDEv }
			DESCRIPTION
				"SCSI device reset."
--#SUMMARY  "[ctl: %d chn: %d tgt: %d :] SCSI device reset."
--#CATEGORY "Status Events"
--#ARGUMENTS { 0, 1, 2 }
--#SEVERITY INFORMATIONAL
--#TIMEINDEX 4
--#STATE   OPERATIONAL
--#STATUS  MANDATORY
			::= 724
		pv660fEvent_PHYSDEV_ACTIVESPARE TRAP-TYPE
			ENTERPRISE aryMgrEvts
			VARIABLES { controllerNameEv, channelNumberEv, targetIDEv }
			DESCRIPTION
				"Active spare found.-"
--#SUMMARY  "[ctl: %d chn: %d tgt: %d :] Active spare found."
--#CATEGORY "Status Events"
--#ARGUMENTS { 0, 1, 2 }
--#SEVERITY INFORMATIONAL
--#TIMEINDEX 4
--#STATE   OPERATIONAL
--#STATUS  MANDATORY
			::= 725
		pv660fEvent_PHYSDEV_WARMSPARE TRAP-TYPE
			ENTERPRISE aryMgrEvts
			VARIABLES { controllerNameEv, channelNumberEv, targetIDEv }
			DESCRIPTION
				"Warm spare found.-"
--#SUMMARY  "[ctl: %d chn: %d tgt: %d :] Warm spare found."
--#CATEGORY "Status Events"
--#ARGUMENTS { 0, 1, 2 }
--#SEVERITY INFORMATIONAL
--#TIMEINDEX 4
--#STATE   OPERATIONAL
--#STATUS  MANDATORY
			::= 726
		pv660fEvent_PHYSDEV_REQSENSE TRAP-TYPE
			ENTERPRISE aryMgrEvts
			VARIABLES { controllerNameEv, channelNumberEv, targetIDEv }
			DESCRIPTION
				"Request Sense Data available."
--#SUMMARY  "[ctl: %d chn: %d tgt: %d :] Request Sense Data available."
--#CATEGORY "IGNORE"
--#ARGUMENTS { 0, 1, 2 }
--#SEVERITY CRITICAL
--#TIMEINDEX 4
--#STATE   NONOPERATIONAL
--#STATUS  OBSOLETE
			::= 727
		pv660fEvent_PHYSDEV_INIT_STARTED TRAP-TYPE
			ENTERPRISE aryMgrEvts
			VARIABLES { controllerNameEv, channelNumberEv, targetIDEv }
			DESCRIPTION
				"Initialization started."
--#SUMMARY  "[ctl: %d chn: %d tgt: %d :] Initialization started."
--#CATEGORY "IGNORE"
--#ARGUMENTS { 0, 1, 2 }
--#SEVERITY INFORMATIONAL
--#TIMEINDEX 4
--#STATE   OPERATIONAL
--#STATUS  OBSOLETE
			::= 728
		pv660fEvent_PHYSDEV_INIT_DONE TRAP-TYPE
			ENTERPRISE aryMgrEvts
			VARIABLES { controllerNameEv, channelNumberEv, targetIDEv }
			DESCRIPTION
				"Initialization completed."
--#SUMMARY  "[ctl: %d chn: %d tgt: %d :] Initialization completed."
--#CATEGORY "IGNORE"
--#ARGUMENTS { 0, 1, 2 }
--#SEVERITY INFORMATIONAL
--#TIMEINDEX 4
--#STATE   OPERATIONAL
--#STATUS  OBSOLETE
			::= 729
		pv660fEvent_PHYSDEV_INIT_FAILED TRAP-TYPE
			ENTERPRISE aryMgrEvts
			VARIABLES { controllerNameEv, channelNumberEv, targetIDEv }
			DESCRIPTION
				"Initialization failed."
--#SUMMARY  "[ctl: %d chn: %d tgt: %d :] Initialization failed."
--#CATEGORY "IGNORE"
--#ARGUMENTS { 0, 1, 2 }
--#SEVERITY MINOR
--#TIMEINDEX 4
--#STATE   OPERATIONAL
--#STATUS  OBSOLETE
			::= 730
		pv660fEvent_PHYSDEV_INIT_CANCELED TRAP-TYPE
			ENTERPRISE aryMgrEvts
			VARIABLES { controllerNameEv, channelNumberEv, targetIDEv }
			DESCRIPTION
				"Initialization canceled."
--#SUMMARY  "[ctl: %d chn: %d tgt: %d :] Initialization canceled."
--#CATEGORY "Error Events"
--#ARGUMENTS { 0, 1, 2 }
--#SEVERITY MAJOR
--#TIMEINDEX 4
--#STATE   OPERATIONAL
--#STATUS  MANDATORY
			::= 731
		pv660fEvent_PHYSDEV_WRITEREC_DEAD TRAP-TYPE
			ENTERPRISE aryMgrEvts
			VARIABLES { controllerNameEv, channelNumberEv, targetIDEv }
			DESCRIPTION
				"A hard disk failed because write recovery failed."
--#SUMMARY  "[ctl: %d chn: %d tgt: %d :] A hard disk failed because write recovery failed."
--#CATEGORY "IGNORE"
--#ARGUMENTS { 0, 1, 2 }
--#SEVERITY MAJOR
--#TIMEINDEX 4
--#STATE   OPERATIONAL
--#STATUS  OBSOLETE
			::= 732
		pv660fEvent_PHYSDEV_RESET_DEAD TRAP-TYPE
			ENTERPRISE aryMgrEvts
			VARIABLES { controllerNameEv, channelNumberEv, targetIDEv }
			DESCRIPTION
				"A hard disk failed because SCSI bus reset failed."
--#SUMMARY  "[ctl: %d chn: %d tgt: %d :] A hard disk failed because SCSI bus reset failed."
--#CATEGORY "IGNORE"
--#ARGUMENTS { 0, 1, 2 }
--#SEVERITY MAJOR
--#TIMEINDEX 4
--#STATE   OPERATIONAL
--#STATUS  OBSOLETE
			::= 733
		pv660fEvent_PHYSDEV_DBLCC_DEAD TRAP-TYPE
			ENTERPRISE aryMgrEvts
			VARIABLES { controllerNameEv, channelNumberEv, targetIDEv }
			DESCRIPTION
				"A hard disk failed because double check condition occured."
--#SUMMARY  "[ctl: %d chn: %d tgt: %d :] A hard disk failed because double check condition occured."
--#CATEGORY "IGNORE"
--#ARGUMENTS { 0, 1, 2 }
--#SEVERITY MAJOR
--#TIMEINDEX 4
--#STATE   OPERATIONAL
--#STATUS  OBSOLETE
			::= 734
		pv660fEvent_PHYSDEV_REMOVED_DEAD TRAP-TYPE
			ENTERPRISE aryMgrEvts
			VARIABLES { controllerNameEv, channelNumberEv, targetIDEv }
			DESCRIPTION
				"A hard disk failed because device is missing."
--#SUMMARY  "[ctl: %d chn: %d tgt: %d :] A hard disk failed because device is missing."
--#CATEGORY "IGNORE"
--#ARGUMENTS { 0, 1, 2 }
--#SEVERITY MAJOR
--#TIMEINDEX 4
--#STATE   OPERATIONAL
--#STATUS  OBSOLETE
			::= 735
		pv660fEvent_PHYSDEV_GROSSERR_DEAD TRAP-TYPE
			ENTERPRISE aryMgrEvts
			VARIABLES { controllerNameEv, channelNumberEv, targetIDEv }
			DESCRIPTION
				"A hard disk failed because of gross error on SCSI processor."
--#SUMMARY  "[ctl: %d chn: %d tgt: %d :] A hard disk failed because of gross error on SCSI processor."
--#CATEGORY "IGNORE"
--#ARGUMENTS { 0, 1, 2 }
--#SEVERITY MAJOR
--#TIMEINDEX 4
--#STATE   OPERATIONAL
--#STATUS  OBSOLETE
			::= 736
		pv660fEvent_PHYSDEV_BADTAG_DEAD TRAP-TYPE
			ENTERPRISE aryMgrEvts
			VARIABLES { controllerNameEv, channelNumberEv, targetIDEv }
			DESCRIPTION
				"A hard disk failed because of bad tag from the device."
--#SUMMARY  "[ctl: %d chn: %d tgt: %d :] A hard disk failed because of bad tag from the device."
--#CATEGORY "IGNORE"
--#ARGUMENTS { 0, 1, 2 }
--#SEVERITY MAJOR
--#TIMEINDEX 4
--#STATE   OPERATIONAL
--#STATUS  OBSOLETE
			::= 737
		pv660fEvent_PHYSDEV_SCSITMO_DEAD TRAP-TYPE
			ENTERPRISE aryMgrEvts
			VARIABLES { controllerNameEv, channelNumberEv, targetIDEv }
			DESCRIPTION
				"A hard disk failed because command to the device timed out."
--#SUMMARY  "[ctl: %d chn: %d tgt: %d :] A hard disk failed because command to the device timed out."
--#CATEGORY "IGNORE"
--#ARGUMENTS { 0, 1, 2 }
--#SEVERITY MAJOR
--#TIMEINDEX 4
--#STATE   OPERATIONAL
--#STATUS  OBSOLETE
			::= 738
		pv660fEvent_PHYSDEV_SYSRESET_DEAD TRAP-TYPE
			ENTERPRISE aryMgrEvts
			VARIABLES { controllerNameEv, channelNumberEv, targetIDEv }
			DESCRIPTION
				"A hard disk failed because of the system reset."
--#SUMMARY  "[ctl: %d chn: %d tgt: %d :] A hard disk failed because of the system reset."
--#CATEGORY "IGNORE"
--#ARGUMENTS { 0, 1, 2 }
--#SEVERITY MAJOR
--#TIMEINDEX 4
--#STATE   OPERATIONAL
--#STATUS  OBSOLETE
			::= 739
		pv660fEvent_PHYSDEV_BSYPAR_DEAD TRAP-TYPE
			ENTERPRISE aryMgrEvts
			VARIABLES { controllerNameEv, channelNumberEv, targetIDEv }
			DESCRIPTION
				"A hard disk failed because of busy status or parity error."
--#SUMMARY  "[ctl: %d chn: %d tgt: %d :] A hard disk failed because of busy status or parity error."
--#CATEGORY "IGNORE"
--#ARGUMENTS { 0, 1, 2 }
--#SEVERITY MAJOR
--#TIMEINDEX 4
--#STATE   OPERATIONAL
--#STATUS  OBSOLETE
			::= 740
		pv660fEvent_PHYSDEV_BYCMD_DEAD TRAP-TYPE
			ENTERPRISE aryMgrEvts
			VARIABLES { controllerNameEv, channelNumberEv, targetIDEv }
			DESCRIPTION
				"A hard disk set to failed state by host."
--#SUMMARY  "[ctl: %d chn: %d tgt: %d :] A hard disk set to failed state by host."
--#CATEGORY "IGNORE"
--#ARGUMENTS { 0, 1, 2 }
--#SEVERITY MAJOR
--#TIMEINDEX 4
--#STATE   OPERATIONAL
--#STATUS  OBSOLETE
			::= 741
		pv660fEvent_PHYSDEV_SELTMO_DEAD TRAP-TYPE
			ENTERPRISE aryMgrEvts
			VARIABLES { controllerNameEv, channelNumberEv, targetIDEv }
			DESCRIPTION
				"A hard disk failed because access to the device met with a selection time out."
--#SUMMARY  "[ctl: %d chn: %d tgt: %d :] A hard disk failed because access to the device met with a selection time out."
--#CATEGORY "IGNORE"
--#ARGUMENTS { 0, 1, 2 }
--#SEVERITY MAJOR
--#TIMEINDEX 4
--#STATE   OPERATIONAL
--#STATUS  OBSOLETE
			::= 742
		pv660fEvent_PHYSDEV_SEQERR_DEAD TRAP-TYPE
			ENTERPRISE aryMgrEvts
			VARIABLES { controllerNameEv, channelNumberEv, targetIDEv }
			DESCRIPTION
				"A hard disk failed because of a sequence error in the SCSI bus phase handling."
--#SUMMARY  "[ctl: %d chn: %d tgt: %d :] A hard disk failed because of a sequence error in the SCSI bus phase handling."
--#CATEGORY "IGNORE"
--#ARGUMENTS { 0, 1, 2 }
--#SEVERITY MAJOR
--#TIMEINDEX 4
--#STATE   OPERATIONAL
--#STATUS  OBSOLETE
			::= 743
		pv660fEvent_PHYSDEV_UNKNOWNSTS_DEAD TRAP-TYPE
			ENTERPRISE aryMgrEvts
			VARIABLES { controllerNameEv, channelNumberEv, targetIDEv }
			DESCRIPTION
				"A hard disk failed because device returned an unknown status."
--#SUMMARY  "[ctl: %d chn: %d tgt: %d :] A hard disk failed because device returned an unknown status."
--#CATEGORY "IGNORE"
--#ARGUMENTS { 0, 1, 2 }
--#SEVERITY MAJOR
--#TIMEINDEX 4
--#STATE   OPERATIONAL
--#STATUS  OBSOLETE
			::= 744
		pv660fEvent_PHYSDEV_NOTRDY_DEAD TRAP-TYPE
			ENTERPRISE aryMgrEvts
			VARIABLES { controllerNameEv, channelNumberEv, targetIDEv }
			DESCRIPTION
				"A hard disk failed because device is not ready."
--#SUMMARY  "[ctl: %d chn: %d tgt: %d :] A hard disk failed because device is not ready."
--#CATEGORY "IGNORE"
--#ARGUMENTS { 0, 1, 2 }
--#SEVERITY MAJOR
--#TIMEINDEX 4
--#STATE   OPERATIONAL
--#STATUS  OBSOLETE
			::= 745
		pv660fEvent_PHYSDEV_MISSING_DEAD TRAP-TYPE
			ENTERPRISE aryMgrEvts
			VARIABLES { controllerNameEv, channelNumberEv, targetIDEv }
			DESCRIPTION
				"A hard disk failed because device was not found on start up."
--#SUMMARY  "[ctl: %d chn: %d tgt: %d :] A hard disk failed because device was not found on start up."
--#CATEGORY "IGNORE"
--#ARGUMENTS { 0, 1, 2 }
--#SEVERITY MAJOR
--#TIMEINDEX 4
--#STATE   OPERATIONAL
--#STATUS  OBSOLETE
			::= 746
		pv660fEvent_PHYSDEV_CODWRFAIL_DEAD TRAP-TYPE
			ENTERPRISE aryMgrEvts
			VARIABLES { controllerNameEv, channelNumberEv, targetIDEv }
			DESCRIPTION
				"A hard disk failed because write operation of the 'Configuration On Disk' failed."
--#SUMMARY  "[ctl: %d chn: %d tgt: %d :] A hard disk failed because write operation of the 'Configuration On Disk' failed."
--#CATEGORY "IGNORE"
--#ARGUMENTS { 0, 1, 2 }
--#SEVERITY MAJOR
--#TIMEINDEX 4
--#STATE   OPERATIONAL
--#STATUS  OBSOLETE
			::= 747
		pv660fEvent_PHYSDEV_BDTWRFAIL_DEAD TRAP-TYPE
			ENTERPRISE aryMgrEvts
			VARIABLES { controllerNameEv, channelNumberEv, targetIDEv }
			DESCRIPTION
				"A hard disk failed because write operation of 'Bad Data Table' failed."
--#SUMMARY  "[ctl: %d chn: %d tgt: %d :] A hard disk failed because write operation of 'Bad Data Table' failed."
--#CATEGORY "IGNORE"
--#ARGUMENTS { 0, 1, 2 }
--#SEVERITY MAJOR
--#TIMEINDEX 4
--#STATE   OPERATIONAL
--#STATUS  OBSOLETE
			::= 748
		pv660fEvent_PHYSDEV_OFFLINE TRAP-TYPE
			ENTERPRISE aryMgrEvts
			VARIABLES { controllerNameEv, channelNumberEv, targetIDEv }
			DESCRIPTION
				"Physical device status changed to offline."
--#SUMMARY  "[ctl: %d chn: %d tgt: %d :] Physical device status changed to offline."
--#CATEGORY "Status Events"
--#ARGUMENTS { 0, 1, 2 }
--#SEVERITY MINOR
--#TIMEINDEX 4
--#STATE   OPERATIONAL
--#STATUS  MANDATORY
			::= 749
		pv660fEvent_PHYSDEV_STANDBY TRAP-TYPE
			ENTERPRISE aryMgrEvts
			VARIABLES { controllerNameEv, channelNumberEv, targetIDEv }
			DESCRIPTION
				"Physical device status changed to Hot Spare."
--#SUMMARY  "[ctl: %d chn: %d tgt: %d :] Physical device status changed to Hot Spare."
--#CATEGORY "Status Events"
--#ARGUMENTS { 0, 1, 2 }
--#SEVERITY MINOR
--#TIMEINDEX 4
--#STATE   OPERATIONAL
--#STATUS  MANDATORY
			::= 750
		pv660fEvent_PHYSDEV_REBUILD TRAP-TYPE
			ENTERPRISE aryMgrEvts
			VARIABLES { controllerNameEv, channelNumberEv, targetIDEv }
			DESCRIPTION
				"Physical device status changed to rebuild."
--#SUMMARY  "[ctl: %d chn: %d tgt: %d :] Physical device status changed to rebuild."
--#CATEGORY "Status Events"
--#ARGUMENTS { 0, 1, 2 }
--#SEVERITY MINOR
--#TIMEINDEX 4
--#STATE   OPERATIONAL
--#STATUS  MANDATORY
			::= 751
		pv660fEvent_PHYSDEV_ID_MISMATCH TRAP-TYPE
			ENTERPRISE aryMgrEvts
			VARIABLES { controllerNameEv, channelNumberEv, targetIDEv }
			DESCRIPTION
				"Physical device ID did not match."
--#SUMMARY  "[ctl: %d chn: %d tgt: %d :] Physical device ID did not match."
--#CATEGORY "Status Events"
--#ARGUMENTS { 0, 1, 2 }
--#SEVERITY MINOR
--#TIMEINDEX 4
--#STATE   OPERATIONAL
--#STATUS  MANDATORY
			::= 752
		pv660fEvent_PHYSDEV_FAILED_START TRAP-TYPE
			ENTERPRISE aryMgrEvts
			VARIABLES { controllerNameEv, channelNumberEv, targetIDEv }
			DESCRIPTION
				"Physical device failed to start."
--#SUMMARY  "[ctl: %d chn: %d tgt: %d :] Physical device failed to start."
--#CATEGORY "Status Events"
--#ARGUMENTS { 0, 1, 2 }
--#SEVERITY MINOR
--#TIMEINDEX 4
--#STATE   OPERATIONAL
--#STATUS  MANDATORY
			::= 753
		pv660fEvent_PHYSDEV_OFFSET_SET TRAP-TYPE
			ENTERPRISE aryMgrEvts
			VARIABLES { controllerNameEv, channelNumberEv, targetIDEv }
			DESCRIPTION
				"Physical device negotiated different offset than config."
--#SUMMARY  "[ctl: %d chn: %d tgt: %d :] Physical device negotiated different offset than config."
--#CATEGORY "Status Events"
--#ARGUMENTS { 0, 1, 2 }
--#SEVERITY MINOR
--#TIMEINDEX 4
--#STATE   OPERATIONAL
--#STATUS  MANDATORY
			::= 754
		pv660fEvent_PHYSDEV_SET_BUS_WIDTH TRAP-TYPE
			ENTERPRISE aryMgrEvts
			VARIABLES { controllerNameEv, channelNumberEv, targetIDEv }
			DESCRIPTION
				"Physical device negotiated different bus width than config."
--#SUMMARY  "[ctl: %d chn: %d tgt: %d :] Physical device negotiated different bus width than config."
--#CATEGORY "Status Events"
--#ARGUMENTS { 0, 1, 2 }
--#SEVERITY MINOR
--#TIMEINDEX 4
--#STATE   OPERATIONAL
--#STATUS  MANDATORY
			::= 755
		pv660fEvent_PHYSDEV_MISSING_ONSTARTUP TRAP-TYPE
			ENTERPRISE aryMgrEvts
			VARIABLES { controllerNameEv, channelNumberEv, targetIDEv }
			DESCRIPTION
				"Physical drive missing on startup."
--#SUMMARY  "[ctl: %d chn: %d tgt: %d :] Physical drive missing on startup."
--#CATEGORY "Error Events"
--#ARGUMENTS { 0, 1, 2 }
--#SEVERITY MAJOR
--#TIMEINDEX 4
--#STATE   OPERATIONAL
--#STATUS  MANDATORY
			::= 756
		pv660fEvent_PHYSDEV_REBUILD_START_FAILED TRAP-TYPE
			ENTERPRISE aryMgrEvts
			VARIABLES { controllerNameEv, channelNumberEv, targetIDEv }
			DESCRIPTION
				"Rebuild startup failed due to lower disk capacity."
--#SUMMARY  "[ctl: %d chn: %d tgt: %d :] Rebuild startup failed due to lower disk capacity."
--#CATEGORY "IGNORE"
--#ARGUMENTS { 0, 1, 2 }
--#SEVERITY MINOR
--#TIMEINDEX 4
--#STATE   OPERATIONAL
--#STATUS  OBSOLETE
			::= 757
		pv660fEvent_PHYSDEV_MOVING_TO_OTHER_CHN TRAP-TYPE
			ENTERPRISE aryMgrEvts
			VARIABLES { controllerNameEv, channelNumberEv, targetIDEv }
			DESCRIPTION
				"Physical drive is switching from a channel to the other channel."
--#SUMMARY  "[ctl: %d chn: %d tgt: %d :] Physical drive is switching from a channel to the other channel."
--#CATEGORY "Status Events"
--#ARGUMENTS { 0, 1, 2 }
--#SEVERITY MINOR
--#TIMEINDEX 4
--#STATE   OPERATIONAL
--#STATUS  MANDATORY
			::= 758
		pv660fEvent_PHYSDEV_OFFLINE_DEVICE_MADE_ONLINE TRAP-TYPE
			ENTERPRISE aryMgrEvts
			VARIABLES { controllerNameEv, channelNumberEv, targetIDEv }
			DESCRIPTION
				"Temporary-Dead physical drive is automatically made online."
--#SUMMARY  "[ctl: %d chn: %d tgt: %d :] Temporary-Dead physical drive is automatically made online."
--#CATEGORY "IGNORE"
--#ARGUMENTS { 0, 1, 2 }
--#SEVERITY CRITICAL
--#TIMEINDEX 4
--#STATE   NONOPERATIONAL
--#STATUS  OBSOLETE
			::= 759
		pv660fEvent_PHYSDEV_STANDBY_REBUILD_START TRAP-TYPE
			ENTERPRISE aryMgrEvts
			VARIABLES { controllerNameEv, channelNumberEv, targetIDEv }
			DESCRIPTION
				"A standby rebuild has started."
--#SUMMARY  "[ctl: %d chn: %d tgt: %d :] A standby rebuild has started."
--#CATEGORY "IGNORE"
--#ARGUMENTS { 0, 1, 2 }
--#SEVERITY INFORMATIONAL
--#TIMEINDEX 4
--#STATE   OPERATIONAL
--#STATUS  OBSOLETE
			::= 760
		pv660fEvent_FIBREDEV_LOOPID_SOFTADDR_OCCURRED TRAP-TYPE
			ENTERPRISE aryMgrEvts
			VARIABLES { controllerNameEv, channelNumberEv }
			DESCRIPTION
				"Device Loop Id Conflict (Soft Addressing) Detected."
--#SUMMARY  "[ctl: %d chn: %d :] Device Loop Id Conflict (Soft Addressing) Detected."
--#CATEGORY "Error Events"
--#ARGUMENTS { 0, 1 }
--#SEVERITY MAJOR
--#TIMEINDEX 3
--#STATE   OPERATIONAL
--#STATUS  MANDATORY
			::= 761
		pv660fEvent_SYSDEV_CHECK_START TRAP-TYPE
			ENTERPRISE aryMgrEvts
			VARIABLES { controllerNameEv, virtualDiskNameEv }
			DESCRIPTION
				"Consistency check is started."
--#SUMMARY  "[ctl: %d logdrv: %d :] Consistency check is started."
--#CATEGORY "Status Events"
--#ARGUMENTS { 0, 1 }
--#SEVERITY INFORMATIONAL
--#TIMEINDEX 3
--#STATE   OPERATIONAL
--#STATUS  MANDATORY
			::= 762
		pv660fEvent_SYSDEV_CHECK_DONE TRAP-TYPE
			ENTERPRISE aryMgrEvts
			VARIABLES { controllerNameEv, virtualDiskNameEv }
			DESCRIPTION
				"Consistency check is finished."
--#SUMMARY  "[ctl: %d logdrv: %d :] Consistency check is finished."
--#CATEGORY "Status Events"
--#ARGUMENTS { 0, 1 }
--#SEVERITY INFORMATIONAL
--#TIMEINDEX 3
--#STATE   OPERATIONAL
--#STATUS  MANDATORY
			::= 763
		pv660fEvent_SYSDEV_CHECK_CANCELED TRAP-TYPE
			ENTERPRISE aryMgrEvts
			VARIABLES { controllerNameEv, virtualDiskNameEv }
			DESCRIPTION
				"Consistency check is cancelled."
--#SUMMARY  "[ctl: %d logdrv: %d :] Consistency check is cancelled."
--#CATEGORY "Status Events"
--#ARGUMENTS { 0, 1 }
--#SEVERITY MINOR
--#TIMEINDEX 3
--#STATE   OPERATIONAL
--#STATUS  MANDATORY
			::= 764
		pv660fEvent_SYSDEV_CHECK_ERROR TRAP-TYPE
			ENTERPRISE aryMgrEvts
			VARIABLES { controllerNameEv, virtualDiskNameEv }
			DESCRIPTION
				"Consistency check on logical drive error."
--#SUMMARY "[ctl: %d logdrv: %d :] Consistency check on logical drive error."
--#CATEGORY "Error Events"
--#ARGUMENTS { 0, 1 }
--#SEVERITY CRITICAL
--#TIMEINDEX 3
--#STATE   NONOPERATIONAL
--#STATUS  MANDATORY
			::= 765
		pv660fEvent_SYSDEV_CHECK_SYSDEV_FAILED TRAP-TYPE
			ENTERPRISE aryMgrEvts
			VARIABLES { controllerNameEv, virtualDiskNameEv }
			DESCRIPTION
				"Consistency check on logical drive failed."
--#SUMMARY  "[ctl: %d logdrv: %d :] Consistency check on logical drive failed."
--#CATEGORY "Error Events"
--#ARGUMENTS { 0, 1 }
--#SEVERITY CRITICAL
--#TIMEINDEX 3
--#STATE   NONOPERATIONAL
--#STATUS  MANDATORY
			::= 766
		pv660fEvent_SYSDEV_CHECK_PHYSDEV_FAILED TRAP-TYPE
			ENTERPRISE aryMgrEvts
			VARIABLES { controllerNameEv, virtualDiskNameEv }
			DESCRIPTION
				"Consistency check failed due to physical device failure."
--#SUMMARY  "[ctl: %d logdrv: %d :] Consistency check failed due to physical device failure."
--#CATEGORY "Error Events"
--#ARGUMENTS { 0, 1 }
--#SEVERITY MAJOR
--#TIMEINDEX 3
--#STATE   OPERATIONAL
--#STATUS  MANDATORY
			::= 767
		pv660fEvent_SYSDEV_OFFLINE TRAP-TYPE
			ENTERPRISE aryMgrEvts
			VARIABLES { controllerNameEv, virtualDiskNameEv }
			DESCRIPTION
				"Logical drive has been made offline."
--#SUMMARY  "[ctl: %d logdrv: %d :] Logical drive has been made offline."
--#CATEGORY "Error Events"
--#ARGUMENTS { 0, 1 }
--#SEVERITY MAJOR
--#TIMEINDEX 3
--#STATE   OPERATIONAL
--#STATUS  MANDATORY
			::= 768
		pv660fEvent_SYSDEV_CRITICAL TRAP-TYPE
			ENTERPRISE aryMgrEvts
			VARIABLES { controllerNameEv, virtualDiskNameEv }
			DESCRIPTION
				"Logical drive is critical."
--#SUMMARY  "[ctl: %d logdrv: %d :] Logical drive is critical."
--#CATEGORY "Error Events"
--#ARGUMENTS { 0, 1 }
--#SEVERITY CRITICAL
--#TIMEINDEX 3
--#STATE   NONOPERATIONAL
--#STATUS  MANDATORY
			::= 769
		pv660fEvent_SYSDEV_ONLINE TRAP-TYPE
			ENTERPRISE aryMgrEvts
			VARIABLES { controllerNameEv, virtualDiskNameEv }
			DESCRIPTION
				"Logical drive has been placed online."
--#SUMMARY  "[ctl: %d logdrv: %d :] Logical drive has been placed online."
--#CATEGORY "Status Events"
--#ARGUMENTS { 0, 1 }
--#SEVERITY INFORMATIONAL
--#TIMEINDEX 3
--#STATE   OPERATIONAL
--#STATUS  MANDATORY
			::= 770
		pv660fEvent_SYSDEV_AUTO_REBUILD_START TRAP-TYPE
			ENTERPRISE aryMgrEvts
			VARIABLES { controllerNameEv, virtualDiskNameEv }
			DESCRIPTION
				"An automatic rebuild has started on logical drive."
--#SUMMARY  "[ctl: %d logdrv: %d :] An automatic rebuild has started on logical drive."
--#CATEGORY "IGNORE"
--#ARGUMENTS { 0, 1 }
--#SEVERITY INFORMATIONAL
--#TIMEINDEX 3
--#STATE   OPERATIONAL
--#STATUS  OBSOLETE
			::= 771
		pv660fEvent_SYSDEV_MANUAL_REBUILD_START TRAP-TYPE
			ENTERPRISE aryMgrEvts
			VARIABLES { controllerNameEv, virtualDiskNameEv }
			DESCRIPTION
				"A manual rebuild has started on logical drive."
--#SUMMARY  "[ctl: %d logdrv: %d :] A manual rebuild has started on logical drive."
--#CATEGORY "IGNORE"
--#ARGUMENTS { 0, 1 }
--#SEVERITY INFORMATIONAL
--#TIMEINDEX 3
--#STATE   OPERATIONAL
--#STATUS  OBSOLETE
			::= 772
		pv660fEvent_SYSDEV_REBUILD_DONE TRAP-TYPE
			ENTERPRISE aryMgrEvts
			VARIABLES { controllerNameEv, virtualDiskNameEv }
			DESCRIPTION
				"Rebuild on logical drive is over."
--#SUMMARY  "[ctl: %d logdrv: %d :] Rebuild on logical drive is over."
--#CATEGORY "IGNORE"
--#ARGUMENTS { 0, 1 }
--#SEVERITY INFORMATIONAL
--#TIMEINDEX 3
--#STATE   OPERATIONAL
--#STATUS  OBSOLETE
			::= 773
		pv660fEvent_SYSDEV_REBUILD_CANCELED TRAP-TYPE
			ENTERPRISE aryMgrEvts
			VARIABLES { controllerNameEv, virtualDiskNameEv }
			DESCRIPTION
				"Rebuild on logical drive is cancelled."
--#SUMMARY  "[ctl: %d logdrv: %d :] Rebuild on logical drive is cancelled."
--#CATEGORY "IGNORE"
--#ARGUMENTS { 0, 1 }
--#SEVERITY MINOR
--#TIMEINDEX 3
--#STATE   OPERATIONAL
--#STATUS  OBSOLETE
			::= 774
		pv660fEvent_SYSDEV_REBUILD_ERROR TRAP-TYPE
			ENTERPRISE aryMgrEvts
			VARIABLES { controllerNameEv, virtualDiskNameEv }
			DESCRIPTION
				"Rebuild stopped with error."
--#SUMMARY  "[ctl: %d logdrv: %d :] Rebuild stopped with error."
--#CATEGORY "IGNORE"
--#ARGUMENTS { 0, 1 }
--#SEVERITY CRITICAL
--#TIMEINDEX 3
--#STATE   NONOPERATIONAL
--#STATUS  OBSOLETE
			::= 775
		pv660fEvent_SYSDEV_REBUILD_NEWDEV_FAILED TRAP-TYPE
			ENTERPRISE aryMgrEvts
			VARIABLES { controllerNameEv, virtualDiskNameEv }
			DESCRIPTION
				"Rebuild stopped with error. New device failed."
--#SUMMARY  "[ctl: %d logdrv: %d :] Rebuild stopped with error. New device failed."
--#CATEGORY "IGNORE"
--#ARGUMENTS { 0, 1 }
--#SEVERITY CRITICAL
--#TIMEINDEX 3
--#STATE   NONOPERATIONAL
--#STATUS  OBSOLETE
			::= 776
		pv660fEvent_SYSDEV_REBUILD_SYSDEV_FAILED TRAP-TYPE
			ENTERPRISE aryMgrEvts
			VARIABLES { controllerNameEv, virtualDiskNameEv }
			DESCRIPTION
				"Rebuild stopped because logical drive failed."
--#SUMMARY  "[ctl: %d logdrv: %d :] Rebuild stopped because logical drive failed."
--#CATEGORY "IGNORE"
--#ARGUMENTS { 0, 1 }
--#SEVERITY CRITICAL
--#TIMEINDEX 3
--#STATE   NONOPERATIONAL
--#STATUS  OBSOLETE
			::= 777
		pv660fEvent_SYSDEV_INIT_STARTED TRAP-TYPE
			ENTERPRISE aryMgrEvts
			VARIABLES { controllerNameEv, virtualDiskNameEv }
			DESCRIPTION
				"Logical drive initialization started."
--#SUMMARY  "[ctl: %d logdrv: %d :] Logical drive initialization started."
--#CATEGORY "Status Events"
--#ARGUMENTS { 0, 1 }
--#SEVERITY INFORMATIONAL
--#TIMEINDEX 3
--#STATE   OPERATIONAL
--#STATUS  MANDATORY
			::= 778
		pv660fEvent_SYSDEV_INIT_DONE TRAP-TYPE
			ENTERPRISE aryMgrEvts
			VARIABLES { controllerNameEv, virtualDiskNameEv }
			DESCRIPTION
				"Logical drive initialization done."
--#SUMMARY  "[ctl: %d logdrv: %d :] Logical drive initialization done."
--#CATEGORY "Status Events"
--#ARGUMENTS { 0, 1 }
--#SEVERITY INFORMATIONAL
--#TIMEINDEX 3
--#STATE   OPERATIONAL
--#STATUS  MANDATORY
			::= 779
		pv660fEvent_SYSDEV_INIT_CANCELED TRAP-TYPE
			ENTERPRISE aryMgrEvts
			VARIABLES { controllerNameEv, virtualDiskNameEv }
			DESCRIPTION
				"Logical drive initialization cancelled."
--#SUMMARY  "[ctl: %d logdrv: %d :] Logical drive initialization cancelled."
--#CATEGORY "Status Events"
--#ARGUMENTS { 0, 1 }
--#SEVERITY MINOR
--#TIMEINDEX 3
--#STATE   OPERATIONAL
--#STATUS  MANDATORY
			::= 780
		pv660fEvent_SYSDEV_INIT_FAILED TRAP-TYPE
			ENTERPRISE aryMgrEvts
			VARIABLES { controllerNameEv, virtualDiskNameEv }
			DESCRIPTION
				"Logical drive initialization failed."
--#SUMMARY  "[ctl: %d logdrv: %d :] Logical drive initialization failed."
--#CATEGORY "Error Events"
--#ARGUMENTS { 0, 1 }
--#SEVERITY CRITICAL
--#TIMEINDEX 3
--#STATE   NONOPERATIONAL
--#STATUS  MANDATORY
			::= 781
		pv660fEvent_SYSDEV_FOUND TRAP-TYPE
			ENTERPRISE aryMgrEvts
			VARIABLES { controllerNameEv, virtualDiskNameEv }
			DESCRIPTION
				"A logical drive has been found."
--#SUMMARY  "[ctl: %d logdrv: %d :] A logical drive has been found."
--#CATEGORY "IGNORE"
--#ARGUMENTS { 0, 1 }
--#SEVERITY INFORMATIONAL
--#TIMEINDEX 3
--#STATE   OPERATIONAL
--#STATUS  OBSOLETE
			::= 782
		pv660fEvent_SYSDEV_GONE TRAP-TYPE
			ENTERPRISE aryMgrEvts
			VARIABLES { controllerNameEv, virtualDiskNameEv }
			DESCRIPTION
				"A logical drive has been deleted."
--#SUMMARY  "[ctl: %d logdrv: %d :] A logical drive has been deleted."
--#CATEGORY "IGNORE"
--#ARGUMENTS { 0, 1 }
--#SEVERITY INFORMATIONAL
--#TIMEINDEX 3
--#STATE   OPERATIONAL
--#STATUS  OBSOLETE
			::= 783
		pv660fEvent_SYSDEV_EXPANDCAPACITY_START TRAP-TYPE
			ENTERPRISE aryMgrEvts
			VARIABLES { controllerNameEv, virtualDiskNameEv }
			DESCRIPTION
				"Expand Capacity Started."
--#SUMMARY  "[ctl: %d logdrv: %d :] Expand Capacity Started."
--#CATEGORY "Status Events"
--#ARGUMENTS { 0, 1 }
--#SEVERITY INFORMATIONAL
--#TIMEINDEX 3
--#STATE   OPERATIONAL
--#STATUS  MANDATORY
			::= 784
		pv660fEvent_SYSDEV_EXPANDCAPACITY_DONE TRAP-TYPE
			ENTERPRISE aryMgrEvts
			VARIABLES { controllerNameEv, virtualDiskNameEv }
			DESCRIPTION
				"Expand Capacity Completed."
--#SUMMARY  "[ctl: %d logdrv: %d :] Expand Capacity Completed."
--#CATEGORY "Status Events"
--#ARGUMENTS { 0, 1 }
--#SEVERITY INFORMATIONAL
--#TIMEINDEX 3
--#STATE   OPERATIONAL
--#STATUS  MANDATORY
			::= 785
		pv660fEvent_SYSDEV_EXPANDCAPACITY_ERROR TRAP-TYPE
			ENTERPRISE aryMgrEvts
			VARIABLES { controllerNameEv, virtualDiskNameEv }
			DESCRIPTION
				"Expand Capacity stopped with error."
--#SUMMARY  "[ctl: %d logdrv: %d :] Expand Capacity stopped with error."
--#CATEGORY "Error Events"
--#ARGUMENTS { 0, 1 }
--#SEVERITY CRITICAL
--#TIMEINDEX 3
--#STATE   NONOPERATIONAL
--#STATUS  MANDATORY
			::= 786
		pv660fEvent_SYSDEV_BADBLOCK TRAP-TYPE
			ENTERPRISE aryMgrEvts
			VARIABLES { controllerNameEv, virtualDiskNameEv }
			DESCRIPTION
				"Bad Blocks found."
--#SUMMARY  "[ctl: %d logdrv: %d :] Bad Blocks found."
--#CATEGORY "Error Events"
--#ARGUMENTS { 0, 1 }
--#SEVERITY CRITICAL
--#TIMEINDEX 3
--#STATE   OPERATIONAL
--#STATUS  MANDATORY
			::= 787
		pv660fEvent_SYSDEV_SIZECHANGED TRAP-TYPE
			ENTERPRISE aryMgrEvts
			VARIABLES { controllerNameEv, virtualDiskNameEv }
			DESCRIPTION
				"System drive size changed."
--#SUMMARY  "[ctl: %d logdrv: %d :] System drive size changed."
--#CATEGORY "Status Events"
--#ARGUMENTS { 0, 1 }
--#SEVERITY INFORMATIONAL
--#TIMEINDEX 3
--#STATE   OPERATIONAL
--#STATUS  MANDATORY
			::= 788
		pv660fEvent_SYSDEV_TYPECHANGED TRAP-TYPE
			ENTERPRISE aryMgrEvts
			VARIABLES { controllerNameEv, virtualDiskNameEv }
			DESCRIPTION
				"System drive type changed."
--#SUMMARY  "[ctl: %d logdrv: %d :] System drive type changed."
--#CATEGORY "Status Events"
--#ARGUMENTS { 0, 1 }
--#SEVERITY INFORMATIONAL
--#TIMEINDEX 3
--#STATE   OPERATIONAL
--#STATUS  MANDATORY
			::= 789
		pv660fEvent_SYSDEV_BADDATABLOCK TRAP-TYPE
			ENTERPRISE aryMgrEvts
			VARIABLES { controllerNameEv, virtualDiskNameEv }
			DESCRIPTION
				"Bad data blocks found. Possible data loss."
--#SUMMARY  "[ctl: %d logdrv: %d :] Bad data blocks found. Possible data loss."
--#CATEGORY "IGNORE"
--#ARGUMENTS { 0, 1 }
--#SEVERITY MAJOR
--#TIMEINDEX 3
--#STATE   OPERATIONAL
--#STATUS  OBSOLETE
			::= 790
		pv660fEvent_SYSDEV_WR_LUN_MAP TRAP-TYPE
			ENTERPRISE aryMgrEvts
			VARIABLES { controllerNameEv }
			DESCRIPTION
				"System drive LUN mapping has been written to config."
--#SUMMARY  "[ctl: %d :] System drive LUN mapping has been written to config."
--#CATEGORY "Status Events"
--#ARGUMENTS { 0 }
--#SEVERITY MINOR
--#TIMEINDEX 2
--#STATE   OPERATIONAL
--#STATUS  MANDATORY
			::= 791
		pv660fEvent_SYSDEV_DATAREAD_FROM_BLOCK_IN_BDT TRAP-TYPE
			ENTERPRISE aryMgrEvts
			VARIABLES { controllerNameEv, virtualDiskNameEv }
			DESCRIPTION
				"Attempt to read data from block that is marked in Bad Data Table"
--#SUMMARY  "[ctl: %d logdrv: %d :] Attempt to read data from block that is marked in Bad Data Table"
--#CATEGORY "Error Events"
--#ARGUMENTS { 0, 1 }
--#SEVERITY MAJOR
--#TIMEINDEX 3
--#STATE   OPERATIONAL
--#STATUS  MANDATORY
			::= 792
		pv660fEvent_SYSDEV_DATA_FOR_BLOCK_LOST TRAP-TYPE
			ENTERPRISE aryMgrEvts
			VARIABLES { controllerNameEv, virtualDiskNameEv }
			DESCRIPTION
				"Data for Disk Block has been lost due to Logical Drive problem"
--#SUMMARY "[ctl: %d logdrv: %d :] Data for Disk Block has been lost due to Logical Drive problem"
--#CATEGORY "Error Events"
--#ARGUMENTS { 0, 1 }
--#SEVERITY CRITICAL
--#TIMEINDEX 3
--#STATE   NONOPERATIONAL
--#STATUS  MANDATORY
			::= 793
		pv660fEvent_SYSDEV_OFFLINE_DEVICE_MADE_AVAILABLE_WITH_DATALOSS TRAP-TYPE
			ENTERPRISE aryMgrEvts
			VARIABLES { controllerNameEv, virtualDiskNameEv }
			DESCRIPTION
				"Temporary-Offline RAID5/RAID3 array is available to the user again with the possibility of data loss in the array."
--#SUMMARY  "[ctl: %d logdrv: %d :] Temporary-Offline RAID5/RAID3 array is available to the user again with the possibility of data loss in the array."
--#CATEGORY "IGNORE"
--#ARGUMENTS { 0, 1 }
--#SEVERITY CRITICAL
--#TIMEINDEX 3
--#STATE   NONOPERATIONAL
--#STATUS  OBSOLETE
			::= 794
		pv660fEvent_SYSDEV_OFFLINE_DEVICE_MADE_AVAILABLE TRAP-TYPE
			ENTERPRISE aryMgrEvts
			VARIABLES { controllerNameEv, virtualDiskNameEv }
			DESCRIPTION
				"Temporary-Offline RAID0+1/RAID1/RAID0/JBOD array is available to the user again."
--#SUMMARY  "[ctl: %d logdrv: %d :] Temporary-Offline RAID0+1/RAID1/RAID0/JBOD array is available to the user again."
--#CATEGORY "IGNORE"
--#ARGUMENTS { 0, 1 }
--#SEVERITY CRITICAL
--#TIMEINDEX 3
--#STATE   NONOPERATIONAL
--#STATUS  OBSOLETE
			::= 795
		pv660fEvent_SYSDEV_STANDBY_REBUILD_START TRAP-TYPE
			ENTERPRISE aryMgrEvts
			VARIABLES { controllerNameEv, virtualDiskNameEv }
			DESCRIPTION
				"An standby rebuild has started on logical drive."
--#SUMMARY  "[ctl: %d logdrv: %d :] An standby rebuild has started on logical drive."
--#CATEGORY "IGNORE"
--#ARGUMENTS { 0, 1 }
--#SEVERITY INFORMATIONAL
--#TIMEINDEX 3
--#STATE   OPERATIONAL
--#STATUS  OBSOLETE
			::= 796
		pv660fEvent_FMTFAN_FAILED TRAP-TYPE
			ENTERPRISE aryMgrEvts
			VARIABLES { controllerNameEv }
			DESCRIPTION
				"Fan failure."
--#SUMMARY  "[ctl: %d enclosure: %d unit: %d :] Fan failure."
--#CATEGORY "IGNORE"
--#ARGUMENTS { 0, 1, 2 }
--#SEVERITY MAJOR
--#TIMEINDEX 4
--#STATE   OPERATIONAL
--#STATUS  OBSOLETE
			::= 797
		pv660fEvent_FMTFAN_OK TRAP-TYPE
			ENTERPRISE aryMgrEvts
			VARIABLES { controllerNameEv }
			DESCRIPTION
				"Fan has been restored."
--#SUMMARY  "[ctl: %d enclosure: %d unit: %d :] Fan has been restored."
--#CATEGORY "IGNORE"
--#ARGUMENTS { 0, 1, 2 }
--#SEVERITY INFORMATIONAL
--#TIMEINDEX 4
--#STATE   OPERATIONAL
--#STATUS  OBSOLETE
			::= 798
		pv660fEvent_AEMI_FAN_FAILED TRAP-TYPE
			ENTERPRISE aryMgrEvts
			VARIABLES { controllerNameEv, channelNumberEv, unitNumberEv }
			DESCRIPTION
				"Fan failure."
--#SUMMARY  "[ctl: %d chn: %d tgt: %d Fan: %d :] Fan failure."
--#CATEGORY "Error Events"
--#ARGUMENTS { 0, 1, 2, 3 }
--#SEVERITY MAJOR
--#TIMEINDEX 5
--#STATE   OPERATIONAL
--#STATUS  MANDATORY
			::= 799
		pv660fEvent_FMTFAN_NOTPRESENT TRAP-TYPE
			ENTERPRISE aryMgrEvts
			VARIABLES { controllerNameEv, enclosureNumberEv }
			DESCRIPTION
				"Storage cabinet fan is not present."
--#SUMMARY  "[ctl: %d enclosure: %d :] Storage cabinet fan is not present."
--#CATEGORY "IGNORE"
--#ARGUMENTS { 0, 1 }
--#SEVERITY INFORMATIONAL
--#TIMEINDEX 3
--#STATE   OPERATIONAL
--#STATUS  OBSOLETE
			::= 800
		pv660fEvent_FMTPOWER_FAILED TRAP-TYPE
			ENTERPRISE aryMgrEvts
			VARIABLES { controllerNameEv }
			DESCRIPTION
				"Power supply failure."
--#SUMMARY  "[ctl: %d enclosure: %d unit: %d :] Power supply failure."
--#CATEGORY "IGNORE"
--#ARGUMENTS { 0, 1, 2 }
--#SEVERITY MAJOR
--#TIMEINDEX 4
--#STATE   OPERATIONAL
--#STATUS  OBSOLETE
			::= 801
		pv660fEvent_FMTPOWER_OK TRAP-TYPE
			ENTERPRISE aryMgrEvts
			VARIABLES { controllerNameEv }
			DESCRIPTION
				"Power supply has been restored."
--#SUMMARY  "[ctl: %d enclosure: %d unit: %d :] Power supply has been restored."
--#CATEGORY "IGNORE"
--#ARGUMENTS { 0, 1, 2 }
--#SEVERITY INFORMATIONAL
--#TIMEINDEX 4
--#STATE   OPERATIONAL
--#STATUS  OBSOLETE
			::= 802
		pv660fEvent_AEMI_PWR_SUPPLY_FAILED TRAP-TYPE
			ENTERPRISE aryMgrEvts
			VARIABLES { controllerNameEv, channelNumberEv, unitNumberEv }
			DESCRIPTION
				"Power supply failure."
--#SUMMARY  "[ctl: %d chn: %d tgt: %d Power Supply: %d :] Power supply failure."
--#CATEGORY "Error Events"
--#ARGUMENTS { 0, 1, 2, 3 }
--#SEVERITY MAJOR
--#TIMEINDEX 5
--#STATE   OPERATIONAL
--#STATUS  MANDATORY
			::= 803
		pv660fEvent_FMTPOWER_NOTPRESENT TRAP-TYPE
			ENTERPRISE aryMgrEvts
			VARIABLES { controllerNameEv, enclosureNumberEv }
			DESCRIPTION
				"Storage cabinet power supply is not present."
--#SUMMARY  "[ctl: %d enclosure: %d :] Storage cabinet power supply is not present."
--#CATEGORY "IGNORE"
--#ARGUMENTS { 0, 1 }
--#SEVERITY INFORMATIONAL
--#TIMEINDEX 3
--#STATE   OPERATIONAL
--#STATUS  OBSOLETE
			::= 804
		pv660fEvent_FMTHEAT_BAD TRAP-TYPE
			ENTERPRISE aryMgrEvts
			VARIABLES { controllerNameEv, channelNumberEv, targetIDEv }
			DESCRIPTION
				"Over temperature. Temperature is above 70 degrees Celsius."
--#SUMMARY  "[ctl: %d chn: %d tgt: %d Heat Sensor: %d :] Over temperature. Temperature is above 70 degrees Celsius."
--#CATEGORY "IGNORE"
--#ARGUMENTS { 0, 1, 2, 3 }
--#SEVERITY MAJOR
--#TIMEINDEX 5
--#STATE   OPERATIONAL
--#STATUS  OBSOLETE
			::= 805
		pv660fEvent_FMTHEAT_CRITICAL TRAP-TYPE
			ENTERPRISE aryMgrEvts
			VARIABLES { controllerNameEv }
			DESCRIPTION
				"Temperature is above 50 degrees Celsius."
--#SUMMARY  "[ctl: %d enclosure: %d unit: %d :] Temperature is above 50 degrees Celsius."
--#CATEGORY "IGNORE"
--#ARGUMENTS { 0, 1, 2 }
--#SEVERITY MINOR
--#TIMEINDEX 4
--#STATE   OPERATIONAL
--#STATUS  OBSOLETE
			::= 806
		pv660fEvent_FMTHEAT_OK TRAP-TYPE
			ENTERPRISE aryMgrEvts
			VARIABLES { controllerNameEv }
			DESCRIPTION
				"Normal temperature has been restored."
--#SUMMARY  "[ctl: %d enclosure: %d unit: %d :] Normal temperature has been restored."
--#CATEGORY "IGNORE"
--#ARGUMENTS { 0, 1, 2 }
--#SEVERITY INFORMATIONAL
--#TIMEINDEX 4
--#STATE   OPERATIONAL
--#STATUS  OBSOLETE
			::= 807
		pv660fEvent_AEMI_OVER_TEMPERATURE TRAP-TYPE
			ENTERPRISE aryMgrEvts
			VARIABLES { controllerNameEv, channelNumberEv, targetIDEv, unitNumberEv }
			DESCRIPTION
				"Over temperature."
--#SUMMARY  "[ctl: %d chn: %d tgt: %d Heat Sensor: %d :] Over temperature."
--#CATEGORY "Error Events"
--#ARGUMENTS { 0, 1, 2, 3 }
--#SEVERITY MAJOR
--#TIMEINDEX 5
--#STATE   OPERATIONAL
--#STATUS  MANDATORY
			::= 808
		pv660fEvent_FMTHEAT_NOTPRESENT TRAP-TYPE
			ENTERPRISE aryMgrEvts
			VARIABLES { controllerNameEv, enclosureNumberEv }
			DESCRIPTION
				"Storage cabinet temperature sensor is not present."
--#SUMMARY  "[ctl: %d enclosure: %d :] Storage cabinet temperature sensor is not present."
--#CATEGORY "IGNORE"
--#ARGUMENTS { 0, 1 }
--#SEVERITY INFORMATIONAL
--#TIMEINDEX 3
--#STATE   OPERATIONAL
--#STATUS  OBSOLETE
			::= 809
		pv660fEvent_FMTSTWK_FAILED TRAP-TYPE
			ENTERPRISE aryMgrEvts
			VARIABLES { controllerNameEv, channelNumberEv }
			DESCRIPTION
				"Storage Works enclosure reported failure state."
--#SUMMARY  "[ctl: %d chn: %d :] Storage Works enclosure reported failure state."
--#CATEGORY "IGNORE"
--#ARGUMENTS { 0, 1 }
--#SEVERITY MAJOR
--#TIMEINDEX 3
--#STATE   OPERATIONAL
--#STATUS  OBSOLETE
			::= 810
		pv660fEvent_FMTSTWK_CRITICAL TRAP-TYPE
			ENTERPRISE aryMgrEvts
			VARIABLES { controllerNameEv, channelNumberEv }
			DESCRIPTION
				"Storage Works enclosure reported critical state."
--#SUMMARY  "[ctl: %d chn: %d :] Storage Works enclosure reported critical state."
--#CATEGORY "IGNORE"
--#ARGUMENTS { 0, 1 }
--#SEVERITY MINOR
--#TIMEINDEX 3
--#STATE   OPERATIONAL
--#STATUS  OBSOLETE
			::= 811
		pv660fEvent_FMTSTWK_OK TRAP-TYPE
			ENTERPRISE aryMgrEvts
			VARIABLES { controllerNameEv, channelNumberEv }
			DESCRIPTION
				"Storage Works enclosure reported normal state."
--#SUMMARY  "[ctl: %d chn: %d :] Storage Works enclosure reported normal state."
--#CATEGORY "IGNORE"
--#ARGUMENTS { 0, 1 }
--#SEVERITY INFORMATIONAL
--#TIMEINDEX 3
--#STATE   OPERATIONAL
--#STATUS  OBSOLETE
			::= 812
		pv660fEvent_FMT_UPS_DISABLED TRAP-TYPE
			ENTERPRISE aryMgrEvts
			VARIABLES { controllerNameEv }
			DESCRIPTION
				"Uninterruptible Power Supply Disabled."
--#SUMMARY  "[ctl: %d :] Uninterruptible Power Supply Disabled."
--#CATEGORY "IGNORE"
--#ARGUMENTS { 0 }
--#SEVERITY INFORMATIONAL
--#TIMEINDEX 2
--#STATE   OPERATIONAL
--#STATUS  OBSOLETE
			::= 813
		pv660fEvent_FMT_UPS_AC_FAIL TRAP-TYPE
			ENTERPRISE aryMgrEvts
			VARIABLES { controllerNameEv }
			DESCRIPTION
				"Uninterruptible Power Supply AC Failed."
--#SUMMARY  "[ctl: %d :] Uninterruptible Power Supply AC Failed."
--#CATEGORY "IGNORE"
--#ARGUMENTS { 0 }
--#SEVERITY INFORMATIONAL
--#TIMEINDEX 2
--#STATE   OPERATIONAL
--#STATUS  OBSOLETE
			::= 814
		pv660fEvent_FMT_UPS_BAT_LOW TRAP-TYPE
			ENTERPRISE aryMgrEvts
			VARIABLES { controllerNameEv }
			DESCRIPTION
				"Uninterruptible Power Supply Battery Low."
--#SUMMARY  "[ctl: %d :] Uninterruptible Power Supply Battery Low."
--#CATEGORY "IGNORE"
--#ARGUMENTS { 0 }
--#SEVERITY MINOR
--#TIMEINDEX 2
--#STATE   OPERATIONAL
--#STATUS  OBSOLETE
			::= 815
		pv660fEvent_FMT_UPS_FAILED TRAP-TYPE
			ENTERPRISE aryMgrEvts
			VARIABLES { controllerNameEv }
			DESCRIPTION
				"Uninterruptible Power Supply Failed."
--#SUMMARY  "[ctl: %d :] Uninterruptible Power Supply Failed."
--#CATEGORY "IGNORE"
--#ARGUMENTS { 0 }
--#SEVERITY MAJOR
--#TIMEINDEX 2
--#STATE   OPERATIONAL
--#STATUS  OBSOLETE
			::= 816
		pv660fEvent_FMT_UPS_OK TRAP-TYPE
			ENTERPRISE aryMgrEvts
			VARIABLES { controllerNameEv }
			DESCRIPTION
				"Uninterruptible Power Supply Normal."
--#SUMMARY  "[ctl: %d :] Uninterruptible Power Supply Normal."
--#CATEGORY "IGNORE"
--#ARGUMENTS { 0 }
--#SEVERITY INFORMATIONAL
--#TIMEINDEX 2
--#STATE   OPERATIONAL
--#STATUS  OBSOLETE
			::= 817
		pv660fEvent_ENCLFAN_FAILED TRAP-TYPE
			ENTERPRISE aryMgrEvts
			VARIABLES { controllerNameEv, enclosureNumberEv, unitNumberEv }
			DESCRIPTION
				"Fan failure."
--#SUMMARY "[ctl: %d enclosure: %d unit: %d :] Fan failure."
--#CATEGORY "Error Events"
--#ARGUMENTS { 0, 1, 2 }
--#SEVERITY MAJOR
--#TIMEINDEX 4
--#STATE   OPERATIONAL
--#STATUS  MANDATORY
			::= 818
		pv660fEvent_ENCLFAN_OK TRAP-TYPE
			ENTERPRISE aryMgrEvts
			VARIABLES { controllerNameEv, enclosureNumberEv, unitNumberEv }
			DESCRIPTION
				"Fan has been restored."
--#SUMMARY  "[ctl: %d enclosure: %d unit: %d :] Fan has been restored."
--#CATEGORY "Status Events"
--#ARGUMENTS { 0, 1, 2 }
--#SEVERITY INFORMATIONAL
--#TIMEINDEX 4
--#STATE   OPERATIONAL
--#STATUS  MANDATORY
			::= 819
		pv660fEvent_ENCLFAN_NOTPRESENT TRAP-TYPE
			ENTERPRISE aryMgrEvts
			VARIABLES { controllerNameEv, enclosureNumberEv, unitNumberEv }
			DESCRIPTION
				"Fan is not present."
--#SUMMARY  "[ctl: %d enclosure: %d unit: %d :] Fan is not present."
--#CATEGORY "Status Events"
--#ARGUMENTS { 0, 1, 2 }
--#SEVERITY INFORMATIONAL
--#TIMEINDEX 4
--#STATE   OPERATIONAL
--#STATUS  MANDATORY
			::= 820
		pv660fEvent_ENCLPOWER_FAILED TRAP-TYPE
			ENTERPRISE aryMgrEvts
			VARIABLES { controllerNameEv, enclosureNumberEv, unitNumberEv }
			DESCRIPTION
				"Power supply failure."
--#SUMMARY  "[ctl: %d enclosure: %d unit: %d :] Power supply failure."
--#CATEGORY "Error Events"
--#ARGUMENTS { 0, 1, 2 }
--#SEVERITY MAJOR
--#TIMEINDEX 4
--#STATE   OPERATIONAL
--#STATUS  MANDATORY
			::= 821
		pv660fEvent_ENCLPOWER_OK TRAP-TYPE
			ENTERPRISE aryMgrEvts
			VARIABLES { controllerNameEv, enclosureNumberEv, unitNumberEv }
			DESCRIPTION
				"Power supply has been restored."
--#SUMMARY  "[ctl: %d enclosure: %d unit: %d :] Power supply has been restored."
--#CATEGORY "Status Events"
--#ARGUMENTS { 0, 1, 2 }
--#SEVERITY INFORMATIONAL
--#TIMEINDEX 4
--#STATE   OPERATIONAL
--#STATUS  MANDATORY
			::= 822
		pv660fEvent_ENCLPOWER_NOTPRESENT TRAP-TYPE
			ENTERPRISE aryMgrEvts
			VARIABLES { controllerNameEv, enclosureNumberEv, unitNumberEv }
			DESCRIPTION
				"Power supply is not present."
--#SUMMARY  "[ctl: %d enclosure: %d unit: %d :] Power supply is not present."
--#CATEGORY "Status Events"
--#ARGUMENTS { 0, 1, 2 }
--#SEVERITY INFORMATIONAL
--#TIMEINDEX 4
--#STATE   OPERATIONAL
--#STATUS  MANDATORY
			::= 823
		pv660fEvent_ENCLHEAT_BAD TRAP-TYPE
			ENTERPRISE aryMgrEvts
			VARIABLES { controllerNameEv, enclosureNumberEv, unitNumberEv }
			DESCRIPTION
				"Temperature is over safe limit. Failure imminent."
--#SUMMARY  "[ctl: %d enclosure: %d unit: %d :] Temperature is over safe limit. Failure imminent."
--#CATEGORY "Error Events"
--#ARGUMENTS { 0, 1, 2 }
--#SEVERITY MAJOR
--#TIMEINDEX 4
--#STATE   OPERATIONAL
--#STATUS  MANDATORY
			::= 824
		pv660fEvent_ENCLHEAT_CRITICAL TRAP-TYPE
			ENTERPRISE aryMgrEvts
			VARIABLES { controllerNameEv, enclosureNumberEv, unitNumberEv }
			DESCRIPTION
				"Temperature is above working limit."
--#SUMMARY "[ctl: %d enclosure: %d unit: %d :] Temperature is above working limit."
--#CATEGORY "Status Events"
--#ARGUMENTS { 0, 1, 2 }
--#SEVERITY MINOR
--#TIMEINDEX 4
--#STATE   OPERATIONAL
--#STATUS  MANDATORY
			::= 825
		pv660fEvent_ENCLHEAT_OK TRAP-TYPE
			ENTERPRISE aryMgrEvts
			VARIABLES { controllerNameEv, enclosureNumberEv, unitNumberEv }
			DESCRIPTION
				"Normal temperature has been restored."
--#SUMMARY  "[ctl: %d enclosure: %d unit: %d :] Normal temperature has been restored."
--#CATEGORY "Status Events"
--#ARGUMENTS { 0, 1, 2 }
--#SEVERITY INFORMATIONAL
--#TIMEINDEX 4
--#STATE   OPERATIONAL
--#STATUS  MANDATORY
			::= 826
		pv660fEvent_ENCLHEAT_NOTPRESENT TRAP-TYPE
			ENTERPRISE aryMgrEvts
			VARIABLES { controllerNameEv, enclosureNumberEv, unitNumberEv }
			DESCRIPTION
				"Temperature sensor is not present."
--#SUMMARY  "[ctl: %d enclosure: %d unit: %d :] Temperature sensor is not present."
--#CATEGORY "Status Events"
--#ARGUMENTS { 0, 1, 2 }
--#SEVERITY INFORMATIONAL
--#TIMEINDEX 4
--#STATE   OPERATIONAL
--#STATUS  MANDATORY
			::= 827
		pv660fEvent_ENCLACCESS_CRITICAL TRAP-TYPE
			ENTERPRISE aryMgrEvts
			VARIABLES { controllerNameEv, enclosureNumberEv }
			DESCRIPTION
				"Enclosure access critical."
--#SUMMARY  "[ctl: %d enclosure: %d :] Enclosure access critical."
--#CATEGORY "Status Events"
--#ARGUMENTS { 0, 1 }
--#SEVERITY MINOR
--#TIMEINDEX 3
--#STATE   OPERATIONAL
--#STATUS  MANDATORY
			::= 828
		pv660fEvent_ENCLACCESS_OK TRAP-TYPE
			ENTERPRISE aryMgrEvts
			VARIABLES { controllerNameEv, enclosureNumberEv }
			DESCRIPTION
				"Enclosure access has been restored."
--#SUMMARY  "[ctl: %d enclosure: %d :] Enclosure access has been restored."
--#CATEGORY "Status Events"
--#ARGUMENTS { 0, 1 }
--#SEVERITY INFORMATIONAL
--#TIMEINDEX 3
--#STATE   OPERATIONAL
--#STATUS  MANDATORY
			::= 829
		pv660fEvent_ENCLACCESS_OFFLINE TRAP-TYPE
			ENTERPRISE aryMgrEvts
			VARIABLES { controllerNameEv, enclosureNumberEv, unitNumberEv }
			DESCRIPTION
				"Enclosure access is offline."
--#SUMMARY "[ctl: %d enclosure: %d unit: %d :] Enclosure access is offline."
--#CATEGORY "Status Events"
--#ARGUMENTS { 0, 1, 2 }
--#SEVERITY MAJOR
--#TIMEINDEX 4
--#STATE OPERATIONAL
--#STATUS MANDATORY
			::= 830
		pv660fEvent_ENCLSES_SOFTADDR_OCCURRED TRAP-TYPE
			ENTERPRISE aryMgrEvts
			VARIABLES { controllerNameEv, enclosureNumberEv }
			DESCRIPTION
				"Enclosure Soft Addressing Detected."
--#SUMMARY  "[ctl: %d enclosure: %d :] Enclosure Soft Addressing Detected."
--#CATEGORY "Error Events"
--#ARGUMENTS { 0, 1 }
--#SEVERITY MAJOR
--#TIMEINDEX 3
--#STATE   OPERATIONAL
--#STATUS  MANDATORY
			::= 831
		pv660fEvent_ENCLACCESS_READY TRAP-TYPE
			ENTERPRISE aryMgrEvts
			VARIABLES { controllerNameEv }
			DESCRIPTION
				"Enclosure services ready"
--#SUMMARY  "[ctl: %d :] Enclosure services ready"
--#CATEGORY "Status Events"
--#ARGUMENTS { 0 }
--#SEVERITY INFORMATIONAL
--#TIMEINDEX 2
--#STATE   OPERATIONAL
--#STATUS  MANDATORY
			::= 832
		pv660fEvent_ENCLHEAT_UNKNOWN TRAP-TYPE
			ENTERPRISE aryMgrEvts
			VARIABLES { controllerNameEv, enclosureNumberEv, unitNumberEv }
			DESCRIPTION
				"Access to temperature sensor has been lost."
--#SUMMARY  "[ctl: %d enclosure: %d unit: %d :] Access to temperature sensor has been lost."
--#CATEGORY "Status Events"
--#ARGUMENTS { 0, 1, 2 }
--#SEVERITY INFORMATIONAL
--#TIMEINDEX 4
--#STATE   OPERATIONAL
--#STATUS  MANDATORY
			::= 833
		pv660fEvent_ENCLPOWER_UNKNOWN TRAP-TYPE
			ENTERPRISE aryMgrEvts
			VARIABLES { controllerNameEv, enclosureNumberEv, unitNumberEv }
			DESCRIPTION
				"Access to power supply status information has been lost."
--#SUMMARY  "[ctl: %d enclosure: %d unit: %d :] Access to power supply status information has been lost."
--#CATEGORY "Status Events"
--#ARGUMENTS { 0, 1, 2 }
--#SEVERITY INFORMATIONAL
--#TIMEINDEX 4
--#STATE   OPERATIONAL
--#STATUS  MANDATORY
			::= 834
		pv660fEvent_ENCLFAN_UNKNOWN TRAP-TYPE
			ENTERPRISE aryMgrEvts
			VARIABLES { controllerNameEv, enclosureNumberEv, unitNumberEv }
			DESCRIPTION
				"Access to fan status information has been lost."
--#SUMMARY  "[ctl: %d enclosure: %d unit: %d :] Access to fan status information has been lost."
--#CATEGORY "Status Events"
--#ARGUMENTS { 0, 1, 2 }
--#SEVERITY INFORMATIONAL
--#TIMEINDEX 4
--#STATE   OPERATIONAL
--#STATUS  MANDATORY
			::= 835
		pv660fEvent_SYSTEM_STARTED TRAP-TYPE
			ENTERPRISE aryMgrEvts
			DESCRIPTION
				"Array management server software started successfully."
--#SUMMARY  "Array management server software started successfully.%d"
--#CATEGORY "Status Events"
--#ARGUMENTS { 0 }
--#SEVERITY INFORMATIONAL
--#TIMEINDEX 1
--#STATE   OPERATIONAL
--#STATUS  MANDATORY
			::= 836
		pv660fEvent_CTLDEV_WRITEBACK_ERROR TRAP-TYPE
			ENTERPRISE aryMgrEvts
			VARIABLES { controllerNameEv }
			DESCRIPTION
				"Write back error."
--#SUMMARY  "[ctl: %d :] Write back error."
--#CATEGORY "Error Events"
--#ARGUMENTS { 0 }
--#SEVERITY CRITICAL
--#TIMEINDEX 2
--#STATE   NONOPERATIONAL
--#STATUS  MANDATORY
			::= 837
		pv660fEvent_CTLDEV_STATE_TABLE_FULL TRAP-TYPE
			ENTERPRISE aryMgrEvts
			VARIABLES { controllerNameEv }
			DESCRIPTION
				"Internal log structures getting full,PLEASE SHUTDOWN AND RESET THE SYSTEM IN THE NEAR FUTURE."
--#SUMMARY  "[ctl: %d :] Internal log structures getting full,PLEASE SHUTDOWN AND RESET THE SYSTEM IN THE NEAR FUTURE."
--#CATEGORY "IGNORE"
--#ARGUMENTS { 0 }
--#SEVERITY MINOR
--#TIMEINDEX 2
--#STATE   OPERATIONAL
--#STATUS  OBSOLETE
			::= 838
		pv660fEvent_CTLDEV_DEAD TRAP-TYPE
			ENTERPRISE aryMgrEvts
			VARIABLES { controllerNameEv }
			DESCRIPTION
				"Controller is dead. System is disconnecting from this controller."
--#SUMMARY  "[ctl: %d :] Controller is dead. System is disconnecting from this controller."
--#CATEGORY "Error Events"
--#ARGUMENTS { 0 }
--#SEVERITY CRITICAL
--#TIMEINDEX 2
--#STATE OPERATIONAL
--#STATUS MANDATORY
			::= 839
		pv660fEvent_CTLDEV_RESET TRAP-TYPE
			ENTERPRISE aryMgrEvts
			VARIABLES { controllerNameEv }
			DESCRIPTION
				"Controller has been reset."
--#SUMMARY  "[ctl: %d :] Controller has been reset."
--#CATEGORY "Status Events"
--#ARGUMENTS { 0 }
--#SEVERITY MINOR
--#TIMEINDEX 2
--#STATE   OPERATIONAL
--#STATUS  MANDATORY
			::= 840
		pv660fEvent_CTLDEV_FOUND TRAP-TYPE
			ENTERPRISE aryMgrEvts
			VARIABLES { controllerNameEv }
			DESCRIPTION
				"Controller is found."
--#SUMMARY "[ctl: %d :] Controller is found."
--#CATEGORY "Status Events"
--#ARGUMENTS { 0 }
--#SEVERITY INFORMATIONAL
--#TIMEINDEX 2
--#STATE   OPERATIONAL
--#STATUS  MANDATORY
			::= 841
		pv660fEvent_CTLDEV_GONE TRAP-TYPE
			ENTERPRISE aryMgrEvts
			VARIABLES { controllerNameEv }
			DESCRIPTION
				"Controller is gone. System is disconnecting from this controller."
--#SUMMARY  "[ctl: %d :] Controller is gone. System is disconnecting from this controller."
--#CATEGORY "Error Events"
--#ARGUMENTS { 0 }
--#SEVERITY CRITICAL
--#TIMEINDEX 2
--#STATE   OPERATIONAL
--#STATUS  MANDATORY
			::= 842
		pv660fEvent_CTLDEV_BBU_FOUND TRAP-TYPE
			ENTERPRISE aryMgrEvts
			VARIABLES { controllerNameEv }
			DESCRIPTION
				"BBU Present."
--#SUMMARY  "[ctl: %d :] BBU Present."
--#CATEGORY "Status Events"
--#ARGUMENTS { 0 }
--#SEVERITY INFORMATIONAL
--#TIMEINDEX 2
--#STATE   OPERATIONAL
--#STATUS  MANDATORY
			::= 843
		pv660fEvent_CTLDEV_BBU_POWER_LOW TRAP-TYPE
			ENTERPRISE aryMgrEvts
			VARIABLES { controllerNameEv }
			DESCRIPTION
				"BBU Power Low."
--#SUMMARY  "[ctl: %d :] BBU Power Low."
--#CATEGORY "Status Events"
--#ARGUMENTS { 0 }
--#SEVERITY MINOR
--#TIMEINDEX 2
--#STATE   OPERATIONAL
--#STATUS  MANDATORY
			::= 844
		pv660fEvent_CTLDEV_BBU_POWER_OK TRAP-TYPE
			ENTERPRISE aryMgrEvts
			VARIABLES { controllerNameEv }
			DESCRIPTION
				"BBU Power OK."
--#SUMMARY  "[ctl: %d :] BBU Power OK."
--#CATEGORY "Status Events"
--#ARGUMENTS { 0 }
--#SEVERITY INFORMATIONAL
--#TIMEINDEX 2
--#STATE   OPERATIONAL
--#STATUS  MANDATORY
			::= 845
		pv660fEvent_CTLDEV_POWER_OFF TRAP-TYPE
			ENTERPRISE aryMgrEvts
			VARIABLES { controllerNameEv }
			DESCRIPTION
				"Controller is powered off."
--#SUMMARY  "[ctl: %d :] Controller powered off."
--#CATEGORY "Status Events"
--#ARGUMENTS { 0 }
--#SEVERITY CRITICAL
--#TIMEINDEX 2
--#STATE   OPERATIONAL
--#STATUS  MANDATORY
			::= 846
		pv660fEvent_CTLDEV_POWER_ON TRAP-TYPE
			ENTERPRISE aryMgrEvts
			VARIABLES { controllerNameEv }
			DESCRIPTION
				"Controller powered on"
--#SUMMARY  "[ctl: %d :] Controller powered on."
--#CATEGORY "Status Events"
--#ARGUMENTS { 0 }
--#SEVERITY INFORMATIONAL
--#TIMEINDEX 2
--#STATE   OPERATIONAL
--#STATUS  MANDATORY
			::= 847
		pv660fEvent_CTLDEV_ONLINE TRAP-TYPE
			ENTERPRISE aryMgrEvts
			VARIABLES { controllerNameEv }
			DESCRIPTION
				"Controller is online."
--#SUMMARY  "[ctl: %d :] Controller is online."
--#CATEGORY "Status Events"
--#ARGUMENTS { 0 }
--#SEVERITY INFORMATIONAL
--#TIMEINDEX 2
--#STATE   OPERATIONAL
--#STATUS  MANDATORY
			::= 848
		pv660fEvent_CTLDEV_OFFLINE TRAP-TYPE
			ENTERPRISE aryMgrEvts
			VARIABLES { controllerNameEv }
			DESCRIPTION
				"Controller is offline."
--#SUMMARY  "[ctl: %d :] Controller is offline."
--#CATEGORY "Error Events"
--#ARGUMENTS { 0 }
--#SEVERITY CRITICAL
--#TIMEINDEX 2
--#STATE   OPERATIONAL
--#STATUS  MANDATORY
			::= 849
		pv660fEvent_CTLDEV_CRITICAL TRAP-TYPE
			ENTERPRISE aryMgrEvts
			VARIABLES { controllerNameEv }
			DESCRIPTION
				"Controller's partner is gone, controller is in failover mode now."
--#SUMMARY  "[ctl: %d :] Controller's partner is gone, controller is in failover mode now."
--#CATEGORY "Status Events"
--#ARGUMENTS { 0 }
--#SEVERITY MINOR
--#TIMEINDEX 2
--#STATE   OPERATIONAL
--#STATUS  MANDATORY
			::= 850
		pv660fEvent_CTLDEV_BBU_RECOND_START TRAP-TYPE
			ENTERPRISE aryMgrEvts
			VARIABLES { controllerNameEv }
			DESCRIPTION
				"BBU reconditioning is started."
--#SUMMARY  "[ctl: %d :] BBU reconditioning is started."
--#CATEGORY "Status Events"
--#ARGUMENTS { 0 }
--#SEVERITY INFORMATIONAL
--#TIMEINDEX 2
--#STATE   OPERATIONAL
--#STATUS  MANDATORY
			::= 851
		pv660fEvent_CTLDEV_BBU_RECOND_DONE TRAP-TYPE
			ENTERPRISE aryMgrEvts
			VARIABLES { controllerNameEv }
			DESCRIPTION
				"BBU reconditioning is finished."
--#SUMMARY  "[ctl: %d :] BBU reconditioning is finished."
--#CATEGORY "Status Events"
--#ARGUMENTS { 0 }
--#SEVERITY INFORMATIONAL
--#TIMEINDEX 2
--#STATE   OPERATIONAL
--#STATUS  MANDATORY
			::= 852
		pv660fEvent_CTLDEV_BBU_RECOND_ABORT TRAP-TYPE
			ENTERPRISE aryMgrEvts
			VARIABLES { controllerNameEv }
			DESCRIPTION
				"BBU reconditioning is canceled."
--#SUMMARY  "[ctl: %d :] BBU reconditioning is canceled."
--#CATEGORY "Status Events"
--#ARGUMENTS { 0 }
--#SEVERITY INFORMATIONAL
--#TIMEINDEX 2
--#STATE   OPERATIONAL
--#STATUS  MANDATORY
			::= 853
		pv660fEvent_CTLDEV_INSTALLATION_ABORTED TRAP-TYPE
			ENTERPRISE aryMgrEvts
			VARIABLES { controllerNameEv }
			DESCRIPTION
				"Installation aborted."
--#SUMMARY  "[ctl: %d :] Installation aborted."
--#CATEGORY "IGNORE"
--#ARGUMENTS { 0 }
--#SEVERITY MAJOR
--#TIMEINDEX 2
--#STATE   OPERATIONAL
--#STATUS  OBSOLETE
			::= 854
		pv660fEvent_CTLDEV_FIRMWARE_MISMATCH TRAP-TYPE
			ENTERPRISE aryMgrEvts
			VARIABLES { controllerNameEv, channelNumberEv, targetIDEv }
			DESCRIPTION
				"Controller firmware mismatch."
--#SUMMARY  "[ctl: %d chn: %d tgt: %d :] Controller firmware mismatch."
--#CATEGORY "Error Events"
--#ARGUMENTS { 0, 1, 2 }
--#SEVERITY MAJOR
--#TIMEINDEX 4
--#STATE   OPERATIONAL
--#STATUS  MANDATORY
			::= 855
		pv660fEvent_CTLDEV_BBU_NORESPONSE TRAP-TYPE
			ENTERPRISE aryMgrEvts
			VARIABLES { controllerNameEv }
			DESCRIPTION
				"BBU removed."
--#SUMMARY  "[ctl: %d chn: %d tgt: %d :] BBU removed."
--#CATEGORY "Status Events"
--#ARGUMENTS { 0, 1, 2 }
--#SEVERITY MINOR
--#TIMEINDEX 4
--#STATE   OPERATIONAL
--#STATUS  MANDATORY
			::= 856
		pv660fEvent_CTLDEV_WARM_BOOT_ERROR TRAP-TYPE
			ENTERPRISE aryMgrEvts
			VARIABLES { controllerNameEv }
			DESCRIPTION
				"WARM BOOT failed."
--#SUMMARY  "[ctl: %d chn: %d tgt: %d :] WARM BOOT failed."
--#CATEGORY "Error Events"
--#ARGUMENTS { 0, 1, 2 }
--#SEVERITY MAJOR
--#TIMEINDEX 4
--#STATE   OPERATIONAL
--#STATUS  MANDATORY
			::= 857
		pv660fEvent_CTLDEV_CONSERV_CACHE_MODE TRAP-TYPE
			ENTERPRISE aryMgrEvts
			VARIABLES { controllerNameEv }
			DESCRIPTION
				"Controller entered Conservative Cache Mode."
--#SUMMARY  "[ctl: %d :] Controller entered Conservative Cache Mode."
--#CATEGORY "Status Events"
--#ARGUMENTS { 0 }
--#SEVERITY MINOR
--#TIMEINDEX 2
--#STATE   OPERATIONAL
--#STATUS  MANDATORY
			::= 858
		pv660fEvent_CTLDEV_NORMAL_CACHE_MODE TRAP-TYPE
			ENTERPRISE aryMgrEvts
			VARIABLES { controllerNameEv }
			DESCRIPTION
				"Controller entered Normal Cache Mode."
--#SUMMARY  "[ctl: %d :] Controller entered Normal Cache Mode."
--#CATEGORY "Status Events"
--#ARGUMENTS { 0 }
--#SEVERITY INFORMATIONAL
--#TIMEINDEX 2
--#STATE   OPERATIONAL
--#STATUS  MANDATORY
			::= 859
		pv660fEvent_CTLDEV_DEV_START_CMPLT TRAP-TYPE
			ENTERPRISE aryMgrEvts
			VARIABLES { controllerNameEv }
			DESCRIPTION
				"Controller Device Start Complete."
--#SUMMARY  "[ctl: %d :] Controller Device Start Complete."
--#CATEGORY "Status Events"
--#ARGUMENTS { 0 }
--#SEVERITY MINOR
--#TIMEINDEX 2
--#STATE   OPERATIONAL
--#STATUS  MANDATORY
			::= 860
		pv660fEvent_CTLDEV_SOFT_ECC_CORRECTED TRAP-TYPE
			ENTERPRISE aryMgrEvts
			VARIABLES { controllerNameEv }
			DESCRIPTION
				"Soft ECC error Corrected."
--#SUMMARY  "[ctl: %d :] Soft ECC error Corrected."
--#CATEGORY "Status Events"
--#ARGUMENTS { 0 }
--#SEVERITY MINOR
--#TIMEINDEX 2
--#STATE   OPERATIONAL
--#STATUS  MANDATORY
			::= 861
		pv660fEvent_CTLDEV_HARD_ECC_CORRECTED TRAP-TYPE
			ENTERPRISE aryMgrEvts
			VARIABLES { controllerNameEv, channelNumberEv, targetIDEv }
			DESCRIPTION
				"Hard ECC error Corrected."
--#SUMMARY  "[ctl: %d chn: %d tgt: %d :] Hard ECC error Corrected."
--#CATEGORY "Status Events"
--#ARGUMENTS { 0, 1, 2 }
--#SEVERITY MINOR
--#TIMEINDEX 4
--#STATE   OPERATIONAL
--#STATUS  MANDATORY
			::= 862
		pv660fEvent_CTLDEV_BBU_RECOND_NEEDED TRAP-TYPE
			ENTERPRISE aryMgrEvts
			VARIABLES { controllerNameEv }
			DESCRIPTION
				"BBU Recondition Suggested."
--#SUMMARY  "[ctl: %d :] BBU Recondition Suggested."
--#CATEGORY "Status Events"
--#ARGUMENTS { 0 }
--#SEVERITY INFORMATIONAL
--#TIMEINDEX 2
--#STATE   OPERATIONAL
--#STATUS  MANDATORY
			::= 863
		pv660fEvent_CTLDEV_REMOVED_PTNR TRAP-TYPE
			ENTERPRISE aryMgrEvts
			VARIABLES { controllerNameEv }
			DESCRIPTION
				"Controller's Partner Has Been Removed."
--#SUMMARY  "[ctl: %d :] Controller's Partner Has Been Removed."
--#CATEGORY "Status Events"
--#ARGUMENTS { 0 }
--#SEVERITY MINOR
--#TIMEINDEX 2
--#STATE   OPERATIONAL
--#STATUS  MANDATORY
			::= 864
		pv660fEvent_CTLDEV_BBU_OUT_OF_SERVICE TRAP-TYPE
			ENTERPRISE aryMgrEvts
			VARIABLES { controllerNameEv }
			DESCRIPTION
				"BBU out of service."
--#SUMMARY  "[ctl: %d :] BBU out of service."
--#CATEGORY "IGNORE"
--#ARGUMENTS { 0 }
--#SEVERITY CRITICAL
--#TIMEINDEX 2
--#STATE   NONOPERATIONAL
--#STATUS  OBSOLETE
			::= 865
		pv660fEvent_CTLDEV_UPDATE_PTNR_STATUS TRAP-TYPE
			ENTERPRISE aryMgrEvts
			VARIABLES { controllerNameEv }
			DESCRIPTION
				"Updated partner's status."
--#SUMMARY  "[ctl: %d :] Updated partner's status."
--#CATEGORY "Status Events"
--#ARGUMENTS { 0 }
--#SEVERITY MINOR
--#TIMEINDEX 2
--#STATE   OPERATIONAL
--#STATUS  MANDATORY
			::= 866
		pv660fEvent_CTLDEV_RELINQUISH_PTNR TRAP-TYPE
			ENTERPRISE aryMgrEvts
			VARIABLES { controllerNameEv }
			DESCRIPTION
				"Relinquished partner."
--#SUMMARY  "[ctl: %d :] Relinquished partner."
--#CATEGORY "Status Events"
--#ARGUMENTS { 0 }
--#SEVERITY MINOR
--#TIMEINDEX 2
--#STATE   OPERATIONAL
--#STATUS  MANDATORY
			::= 867
		pv660fEvent_CTLDEV_INSERTED_PTNR TRAP-TYPE
			ENTERPRISE aryMgrEvts
			VARIABLES { controllerNameEv }
			DESCRIPTION
				"Inserted Partner."
--#SUMMARY  "[ctl: %d :] Inserted Partner."
--#CATEGORY "Status Events"
--#ARGUMENTS { 0 }
--#SEVERITY MINOR
--#TIMEINDEX 2
--#STATE   OPERATIONAL
--#STATUS  MANDATORY
			::= 868
		pv660fEvent_CTLDEV_DUAL_ENABLED TRAP-TYPE
			ENTERPRISE aryMgrEvts
			VARIABLES { controllerNameEv }
			DESCRIPTION
				"Dual Controllers Enabled."
--#SUMMARY  "[ctl: %d :] Dual Controllers Enabled."
--#CATEGORY "Status Events"
--#ARGUMENTS { 0 }
--#SEVERITY MINOR
--#TIMEINDEX 2
--#STATE   OPERATIONAL
--#STATUS  MANDATORY
			::= 869
		pv660fEvent_CTLDEV_KILL_PTNR TRAP-TYPE
			ENTERPRISE aryMgrEvts
			VARIABLES { controllerNameEv }
			DESCRIPTION
				"Killed Partner."
--#SUMMARY  "[ctl: %d :] Killed Partner."
--#CATEGORY "Status Events"
--#ARGUMENTS { 0 }
--#SEVERITY MINOR
--#TIMEINDEX 2
--#STATE   OPERATIONAL
--#STATUS  MANDATORY
			::= 870
		pv660fEvent_CTLDEV_NEXUS TRAP-TYPE
			ENTERPRISE aryMgrEvts
			VARIABLES { controllerNameEv }
			DESCRIPTION
				"Dual Controllers entered Nexus."
--#SUMMARY  "[ctl: %d :] Dual Controllers entered Nexus."
--#CATEGORY "Status Events"
--#ARGUMENTS { 0 }
--#SEVERITY MINOR
--#TIMEINDEX 2
--#STATE   OPERATIONAL
--#STATUS  MANDATORY
			::= 871
		pv660fEvent_CTLDEV_BAD_BOOTROM_IMAGE TRAP-TYPE
			ENTERPRISE aryMgrEvts
			VARIABLES { controllerNameEv }
			DESCRIPTION
				"Controller Boot ROM Image needs to be reloaded."
--#SUMMARY  "[ctl: %d :] Controller Boot ROM Image needs to be reloaded."
--#CATEGORY "Error Events"
--#ARGUMENTS { 0 }
--#SEVERITY MAJOR
--#TIMEINDEX 2
--#STATE   OPERATIONAL
--#STATUS  MANDATORY
			::= 872
		pv660fEvent_CTLDEV_BAD_MAC_ADDRESS TRAP-TYPE
			ENTERPRISE aryMgrEvts
			VARIABLES { controllerNameEv }
			DESCRIPTION
				"Controller is using default non-unique world-wide name."
--#SUMMARY  "[ctl: %d :] Controller is using default non-unique world-wide name."
--#CATEGORY "Error Events"
--#ARGUMENTS { 0 }
--#SEVERITY CRITICAL
--#TIMEINDEX 2
--#STATE   OPERATIONAL
--#STATUS  MANDATORY
			::= 873
		pv660fEvent_CTLDEV_MIRROR_RACE_RECOVERY_FAILED TRAP-TYPE
			ENTERPRISE aryMgrEvts
			VARIABLES { controllerNameEv }
			DESCRIPTION
				"Mirror Race recovery failed."
--#SUMMARY  "[ctl: %d :] Mirror Race recovery failed."
--#CATEGORY "IGNORE"
--#ARGUMENTS { 0 }
--#SEVERITY CRITICAL
--#TIMEINDEX 2
--#STATE   NONOPERATIONAL
--#STATUS  OBSOLETE
			::= 874
		pv660fEvent_CTLDEV_MIRROR_CRITICAL_DRIVE TRAP-TYPE
			ENTERPRISE aryMgrEvts
			VARIABLES { controllerNameEv }
			DESCRIPTION
				"Mirror Race on critical drive."
--#SUMMARY  "[ctl: %d :] Mirror Race on critical drive."
--#CATEGORY "IGNORE"
--#ARGUMENTS { 0 }
--#SEVERITY CRITICAL
--#TIMEINDEX 2
--#STATE   OPERATIONAL
--#STATUS  OBSOLETE
			::= 875
		pv660fEvent_SYSTEM_STARTED_NEW TRAP-TYPE
			ENTERPRISE aryMgrEvts
			DESCRIPTION
				"System started.-"
--#SUMMARY  "System started.-%d"
--#CATEGORY "IGNORE"
--#ARGUMENTS { 0 }
--#SEVERITY INFORMATIONAL
--#TIMEINDEX 1
--#STATE   OPERATIONAL
--#STATUS  OBSOLETE
			::= 876
		pv660fEvent_SYSTEM_SIZE_TABLE_FULL TRAP-TYPE
			ENTERPRISE aryMgrEvts
			DESCRIPTION
				"Size table full."
--#SUMMARY  "Size table full.-%d"
--#CATEGORY "IGNORE"
--#ARGUMENTS { 0 }
--#SEVERITY INFORMATIONAL
--#TIMEINDEX 1
--#STATE   OPERATIONAL
--#STATUS  OBSOLETE
			::= 877
		pv660fEvent_SYSTEM_USER_LOGGED_IN TRAP-TYPE
			ENTERPRISE aryMgrEvts
			DESCRIPTION
				"User logged in."
--#SUMMARY  "User logged in.-%d"
--#CATEGORY "IGNORE"
--#ARGUMENTS { 0 }
--#SEVERITY INFORMATIONAL
--#TIMEINDEX 1
--#STATE   OPERATIONAL
--#STATUS  OBSOLETE
			::= 878
		pv660fEvent_SYSTEM_USER_LOGGED_OUT TRAP-TYPE
			ENTERPRISE aryMgrEvts
			DESCRIPTION
				"User logged out.-"
--#SUMMARY  "User logged out.-%d"
--#CATEGORY "IGNORE"
--#ARGUMENTS { 0 }
--#SEVERITY INFORMATIONAL
--#TIMEINDEX 1
--#STATE   OPERATIONAL
--#STATUS  OBSOLETE
			::= 879
		pv660fEvent_SYSTEM_ALIVE TRAP-TYPE
			ENTERPRISE aryMgrEvts
			DESCRIPTION
				"Server alive."
--#SUMMARY  "Server alive.%d"
--#CATEGORY "IGNORE"
--#ARGUMENTS { 0 }
--#SEVERITY INFORMATIONAL
--#TIMEINDEX 1
--#STATE   OPERATIONAL
--#STATUS  OBSOLETE
			::= 880
		pv660fEvent_SYSTEM_DEAD TRAP-TYPE
			ENTERPRISE aryMgrEvts
			DESCRIPTION
				"Lost connection to server, or server is down."
--#SUMMARY  "Lost connection to server, or server is down.%d"
--#CATEGORY "Error Events"
--#ARGUMENTS { 0 }
--#SEVERITY MAJOR
--#TIMEINDEX 1
--#STATE   OPERATIONAL
--#STATUS  MANDATORY
			::= 881
		pv660fEvent_AUTOBOOT_CHANGED TRAP-TYPE
			ENTERPRISE aryMgrEvts
			VARIABLES { controllerNameEv }
			DESCRIPTION
				"Automatic reboot count has changed."
--#SUMMARY  "[ctl: %d :] Automatic reboot count has changed."
--#CATEGORY "Status Events"
--#ARGUMENTS { 0 }
--#SEVERITY INFORMATIONAL
--#TIMEINDEX 2
--#STATE   OPERATIONAL
--#STATUS  MANDATORY
			::= 882
		pv660fEvent_CHANNEL_FAILED TRAP-TYPE
			ENTERPRISE aryMgrEvts
			VARIABLES { controllerNameEv, channelNumberEv }
			DESCRIPTION
				"Channel Failed."
--#SUMMARY  "[ctl: %d chn: %d :] Channel Failed."
--#CATEGORY "Status Events"
--#ARGUMENTS { 0, 1 }
--#SEVERITY MINOR
--#TIMEINDEX 3
--#STATE   OPERATIONAL
--#STATUS  MANDATORY
			::= 883
		pv660fEvent_CHANNEL_OK TRAP-TYPE
			ENTERPRISE aryMgrEvts
			VARIABLES { controllerNameEv, channelNumberEv }
			DESCRIPTION
				"Channel Online."
--#SUMMARY  "[ctl: %d chn: %d :] Channel Online."
--#CATEGORY "Status Events"
--#ARGUMENTS { 0, 1 }
--#SEVERITY MINOR
--#TIMEINDEX 3
--#STATE   OPERATIONAL
--#STATUS  MANDATORY
			::= 884
		pv660fEvent_CHANNEL_SCSI_BUS_DEAD TRAP-TYPE
			ENTERPRISE aryMgrEvts
			VARIABLES { controllerNameEv, channelNumberEv }
			DESCRIPTION
				"Back End SCSI Bus Dead."
--#SUMMARY  "[ctl: %d chn: %d :] Back End SCSI Bus Dead."
--#CATEGORY "IGNORE"
--#ARGUMENTS { 0, 1 }
--#SEVERITY MAJOR
--#TIMEINDEX 3
--#STATE   OPERATIONAL
--#STATUS  OBSOLETE
			::= 885
		pv660fEvent_CHANNEL_SCSI_BUS_ALIVE TRAP-TYPE
			ENTERPRISE aryMgrEvts
			VARIABLES { controllerNameEv, channelNumberEv }
			DESCRIPTION
				"Back End SCSI Bus Alive."
--#SUMMARY  "[ctl: %d chn: %d :] Back End SCSI Bus Alive."
--#CATEGORY "IGNORE"
--#ARGUMENTS { 0, 1 }
--#SEVERITY INFORMATIONAL
--#TIMEINDEX 3
--#STATE   OPERATIONAL
--#STATUS  OBSOLETE
			::= 886
		pv660fEvent_CHANNEL_FIBER_DEAD TRAP-TYPE
			ENTERPRISE aryMgrEvts
			VARIABLES { controllerNameEv, channelNumberEv }
			DESCRIPTION
				"Back End Fibre Dead."
--#SUMMARY  "[ctl: %d chn: %d :] Back End Fibre Dead."
--#CATEGORY "Error Events"
--#ARGUMENTS { 0, 1 }
--#SEVERITY MAJOR
--#TIMEINDEX 3
--#STATE   OPERATIONAL
--#STATUS  MANDATORY
			::= 887
		pv660fEvent_CHANNEL_FIBER_ALIVE TRAP-TYPE
			ENTERPRISE aryMgrEvts
			VARIABLES { controllerNameEv, channelNumberEv }
			DESCRIPTION
				"Back End Fibre Alive."
--#SUMMARY  "[ctl: %d chn: %d :] Back End Fibre Alive."
--#CATEGORY "Status Events"
--#ARGUMENTS { 0, 1 }
--#SEVERITY INFORMATIONAL
--#TIMEINDEX 3
--#STATE   OPERATIONAL
--#STATUS  MANDATORY
			::= 888
		pv660fEvent_LOG_EMPTY TRAP-TYPE
			ENTERPRISE aryMgrEvts
			VARIABLES { controllerNameEv }
			DESCRIPTION
				"Event Log Empty."
--#SUMMARY  "[ctl: %d :] Event Log Empty."
--#CATEGORY "IGNORE"
--#ARGUMENTS { 0 }
--#SEVERITY MINOR
--#TIMEINDEX 2
--#STATE   OPERATIONAL
--#STATUS  OBSOLETE
			::= 889
		pv660fEvent_LOG_OUT_SYNC TRAP-TYPE
			ENTERPRISE aryMgrEvts
			VARIABLES { controllerNameEv }
			DESCRIPTION
				"Event Log Entries Lost."
--#SUMMARY  "[ctl: %d :] Event Log Entries Lost."
--#CATEGORY "Status Events"
--#ARGUMENTS { 0 }
--#SEVERITY MINOR
--#TIMEINDEX 2
--#STATE   OPERATIONAL
--#STATUS  MANDATORY
			::= 890
		pv660fEvent_LOG_REQUEST_SENSE TRAP-TYPE
			ENTERPRISE aryMgrEvts
			VARIABLES { controllerNameEv, channelNumberEv, targetIDEv }
			DESCRIPTION
				"Request Sense"
--#SUMMARY  "[ctl: %d chn: %d tgt: %d :] Request Sense"
--#CATEGORY "Status Events"
--#ARGUMENTS { 0, 1, 2 }
--#SEVERITY MINOR
--#TIMEINDEX 4
--#STATE   OPERATIONAL
--#STATUS  MANDATORY
			::= 891
		pv660fEvent_LOG_SET_RTC TRAP-TYPE
			ENTERPRISE aryMgrEvts
			VARIABLES { controllerNameEv, channelNumberEv }
			DESCRIPTION
				"Set Real Time Clock."
--#SUMMARY  "[ctl: %d chn: %d :] Set Real Time Clock."
--#CATEGORY "Status Events"
--#ARGUMENTS { 0, 1 }
--#SEVERITY MINOR
--#TIMEINDEX 3
--#STATE   OPERATIONAL
--#STATUS  MANDATORY
			::= 892
		pv660fEvent_CFG_NEW TRAP-TYPE
			ENTERPRISE aryMgrEvts
			VARIABLES { controllerNameEv }
			DESCRIPTION
				"New Configuration Received."
--#SUMMARY  "[ctl: %d :] New Configuration Received."
--#CATEGORY "Status Events"
--#ARGUMENTS { 0 }
--#SEVERITY MINOR
--#TIMEINDEX 2
--#STATE   OPERATIONAL
--#STATUS  MANDATORY
			::= 893
		pv660fEvent_CFG_CLEAR TRAP-TYPE
			ENTERPRISE aryMgrEvts
			VARIABLES { controllerNameEv }
			DESCRIPTION
				"Configuration Cleared."
--#SUMMARY  "[ctl: %d :] Configuration Cleared."
--#CATEGORY "Status Events"
--#ARGUMENTS { 0 }
--#SEVERITY MINOR
--#TIMEINDEX 2
--#STATE   OPERATIONAL
--#STATUS  MANDATORY
			::= 894
		pv660fEvent_CFG_INVALID TRAP-TYPE
			ENTERPRISE aryMgrEvts
			VARIABLES { controllerNameEv }
			DESCRIPTION
				"Configuration Invalid."
--#SUMMARY  "[ctl: %d :] Configuration Invalid."
--#CATEGORY "Status Events"
--#ARGUMENTS { 0 }
--#SEVERITY MINOR
--#TIMEINDEX 2
--#STATE   OPERATIONAL
--#STATUS  MANDATORY
			::= 895
		pv660fEvent_CFG_COD_ACCESS_ERROR TRAP-TYPE
			ENTERPRISE aryMgrEvts
			VARIABLES { controllerNameEv }
			DESCRIPTION
				"Configuration On Disk Access Error."
--#SUMMARY  "[ctl: %d :] Configuration On Disk Access Error."
--#CATEGORY "Status Events"
--#ARGUMENTS { 0 }
--#SEVERITY MINOR
--#TIMEINDEX 2
--#STATE   OPERATIONAL
--#STATUS  MANDATORY
			::= 896
		pv660fEvent_CFG_COD_CONVERTED TRAP-TYPE
			ENTERPRISE aryMgrEvts
			VARIABLES { controllerNameEv }
			DESCRIPTION
				"Configuration On Disk Converted."
--#SUMMARY  "[ctl: %d :] Configuration On Disk Converted."
--#CATEGORY "Status Events"
--#ARGUMENTS { 0 }
--#SEVERITY MINOR
--#TIMEINDEX 2
--#STATE   OPERATIONAL
--#STATUS  MANDATORY
			::= 897
		pv660fEvent_CFG_COD_IMPORT_FAILED TRAP-TYPE
			ENTERPRISE aryMgrEvts
			VARIABLES { controllerNameEv }
			DESCRIPTION
				"Configuration On Disk Import Failed."
--#SUMMARY  "[ctl: %d :] Configuration On Disk Import Failed."
--#CATEGORY "Status Events"
--#ARGUMENTS { 0 }
--#SEVERITY MINOR
--#TIMEINDEX 2
--#STATE   OPERATIONAL
--#STATUS  MANDATORY
			::= 898
		pv660fEvent_DEBUG_DUMP_GENERATED TRAP-TYPE
			ENTERPRISE aryMgrEvts
			VARIABLES { controllerNameEv }
			DESCRIPTION
				"A Debug Dump exists on this system."
--#SUMMARY  "[ctl: %d :] A Debug Dump exists on this system."
--#CATEGORY "Status Events"
--#ARGUMENTS { 0 }
--#SEVERITY INFORMATIONAL
--#TIMEINDEX 2
--#STATE   OPERATIONAL
--#STATUS  MANDATORY
			::= 899
		pv660fEvent_DEBUG_DUMP_GENERATED_PARTNER TRAP-TYPE
			ENTERPRISE aryMgrEvts
			VARIABLES { controllerNameEv }
			DESCRIPTION
				"A Debug Dump exists on this system."
--#SUMMARY  "[ctl: %d :] A Debug Dump exists on this system."
--#CATEGORY "Status Events"
--#ARGUMENTS { 0 }
--#SEVERITY INFORMATIONAL
--#TIMEINDEX 2
--#STATE   OPERATIONAL
--#STATUS  MANDATORY
			::= 900
		pv660fEvent_FATAL_HANG TRAP-TYPE
			ENTERPRISE aryMgrEvts
			DESCRIPTION
				"Internal Controller is in the hung state."
--#SUMMARY  "Internal Controller is in the hung state.%d"
--#CATEGORY "IGNORE"
--#ARGUMENTS { 0 }
--#SEVERITY MAJOR
--#TIMEINDEX 1
--#STATE   OPERATIONAL
--#STATUS  OBSOLETE
			::= 901
		pv660fEvent_FATAL_BRKP TRAP-TYPE
			ENTERPRISE aryMgrEvts
			DESCRIPTION
				"Internal Controller has encountered a Firmware breakpoint."
--#SUMMARY  "Internal Controller has encountered a Firmware breakpoint.%d"
--#CATEGORY "IGNORE"
--#ARGUMENTS { 0 }
--#SEVERITY MAJOR
--#TIMEINDEX 1
--#STATE   OPERATIONAL
--#STATUS  OBSOLETE
			::= 902
		pv660fEvent_I960_HW_ERR TRAP-TYPE
			ENTERPRISE aryMgrEvts
			DESCRIPTION
				"Internal Controller has encountered i960 processor specific error."
--#SUMMARY  "Internal Controller has encountered i960 processor specific error.%d"
--#CATEGORY "IGNORE"
--#ARGUMENTS { 0 }
--#SEVERITY MAJOR
--#TIMEINDEX 1
--#STATE   OPERATIONAL
--#STATUS  OBSOLETE
			::= 903
		pv660fEvent_SARM_HW_ERR TRAP-TYPE
			ENTERPRISE aryMgrEvts
			DESCRIPTION
				"Internal Controller has encountered Strong-ARM processor specific error"
--#SUMMARY  "Internal Controller has encountered Strong-ARM processor specific error%d"
--#CATEGORY "IGNORE"
--#ARGUMENTS { 0 }
--#SEVERITY MAJOR
--#TIMEINDEX 1
--#STATE   OPERATIONAL
--#STATUS  OBSOLETE
			::= 904
		pv660fEvent_SYSDEV_BG_INIT_STARTED TRAP-TYPE
			ENTERPRISE aryMgrEvts
			VARIABLES { controllerNameEv, virtualDiskNameEv }
			DESCRIPTION
				"Logical drive background initialization started."
--#SUMMARY  "[ctl: %d logdrv: %d :] Logical drive background initialization started."
--#CATEGORY "Status Events"
--#ARGUMENTS { 0, 1 }
--#SEVERITY INFORMATIONAL
--#TIMEINDEX 3
--#STATE   OPERATIONAL
--#STATUS  MANDATORY
			::= 905
		pv660fEvent_SYSDEV_BG_INIT_STOPPED TRAP-TYPE
			ENTERPRISE aryMgrEvts
			VARIABLES { controllerNameEv, virtualDiskNameEv }
			DESCRIPTION
				"Logical drive background initialization stopped."
--#SUMMARY  "[ctl: %d logdrv: %d :] Logical drive background initialization stopped."
--#CATEGORY "Status Events"
--#ARGUMENTS { 0, 1 }
--#SEVERITY INFORMATIONAL
--#TIMEINDEX 3
--#STATE   OPERATIONAL
--#STATUS  MANDATORY
			::= 906
		pv660fEvent_SYSDEV_BG_INIT_PAUSED TRAP-TYPE
			ENTERPRISE aryMgrEvts
			VARIABLES { controllerNameEv, virtualDiskNameEv }
			DESCRIPTION
				"Logical drive background initialization paused."
--#SUMMARY  "[ctl: %d logdrv: %d :] Logical drive background initialization paused."
--#CATEGORY "Status Events"
--#ARGUMENTS { 0, 1 }
--#SEVERITY INFORMATIONAL
--#TIMEINDEX 3
--#STATE   OPERATIONAL
--#STATUS  MANDATORY
			::= 907
		pv660fEvent_SYSDEV_BG_INIT_RESTARTED TRAP-TYPE
			ENTERPRISE aryMgrEvts
			VARIABLES { controllerNameEv, virtualDiskNameEv }
			DESCRIPTION
				"Logical drive background initialization restarted."
--#SUMMARY  "[ctl: %d logdrv: %d :] Logical drive background initialization restarted."
--#CATEGORY "Status Events"
--#ARGUMENTS { 0, 1 }
--#SEVERITY INFORMATIONAL
--#TIMEINDEX 3
--#STATE   OPERATIONAL
--#STATUS  MANDATORY
			::= 908
		pv660fEvent_SYSDEV_BG_INIT_FAILED TRAP-TYPE
			ENTERPRISE aryMgrEvts
			VARIABLES { controllerNameEv, virtualDiskNameEv }
			DESCRIPTION
				"Logical drive background initialization failed."
--#SUMMARY  "[ctl: %d logdrv: %d :] Logical drive background initialization failed."
--#CATEGORY "Error Events"
--#ARGUMENTS { 0, 1 }
--#SEVERITY CRITICAL
--#TIMEINDEX 3
--#STATE   NONOPERATIONAL
--#STATUS  MANDATORY
			::= 909
		pv660fEvent_SYSDEV_BG_INIT_COMPLETED TRAP-TYPE
			ENTERPRISE aryMgrEvts
			VARIABLES { controllerNameEv, virtualDiskNameEv }
			DESCRIPTION
				"Logical drive background initialization completed."
--#SUMMARY  "[ctl: %d logdrv: %d :] Logical drive background initialization completed."
--#CATEGORY "Status Events"
--#ARGUMENTS { 0, 1 }
--#SEVERITY INFORMATIONAL
--#TIMEINDEX 3
--#STATE   OPERATIONAL
--#STATUS  MANDATORY
			::= 910
		pv660fEvent_CTLDEV_BBU_CALIBRATE_START TRAP-TYPE
			ENTERPRISE aryMgrEvts
			VARIABLES { controllerNameEv }
			DESCRIPTION
				"BBU calibration cycle started."
--#SUMMARY  "[ctl: %d :] BBU calibration cycle started."
--#CATEGORY "Status Events"
--#ARGUMENTS { 0 }
--#SEVERITY INFORMATIONAL
--#TIMEINDEX 2
--#STATE   OPERATIONAL
--#STATUS  MANDATORY
			::= 911
		pv660fEvent_CTLDEV_BBU_CALIBRATE_DONE TRAP-TYPE
			ENTERPRISE aryMgrEvts
			VARIABLES { controllerNameEv }
			DESCRIPTION
				"BBU calibration cycle finished."
--#SUMMARY "[ctl: %d :] BBU calibration cycle finished."
--#CATEGORY "Status Events"
--#ARGUMENTS { 0 }
--#SEVERITY INFORMATIONAL
--#TIMEINDEX 2
--#STATE   OPERATIONAL
--#STATUS  MANDATORY
			::= 912
		pv660fEvent_CTLDEV_BBU_CALIBRATE_ABORT TRAP-TYPE
			ENTERPRISE aryMgrEvts
			VARIABLES { controllerNameEv }
			DESCRIPTION
				"BBU calibration cycle is canceled."
--#SUMMARY  "[ctl: %d :] BBU calibration cycle is canceled."
--#CATEGORY "Status Events"
--#ARGUMENTS { 0 }
--#SEVERITY INFORMATIONAL
--#TIMEINDEX 2
--#STATE   OPERATIONAL
--#STATUS  MANDATORY
			::= 913
		pv660fEvent_CTLDEV_BBU_NO_BATTERY TRAP-TYPE
			ENTERPRISE aryMgrEvts
			VARIABLES { controllerNameEv }
			DESCRIPTION
				"BBU battery not present."
--#SUMMARY  "[ctl: %d :] BBU battery not present."
--#CATEGORY "Status Events"
--#ARGUMENTS { 0 }
--#SEVERITY INFORMATIONAL
--#TIMEINDEX 2
--#STATE   OPERATIONAL
--#STATUS  MANDATORY
			::= 914
		pv660fEvent_SYSDEV_BBULOW_POSSIBLE_DATA_LOSS TRAP-TYPE
			ENTERPRISE aryMgrEvts
			VARIABLES { controllerNameEv, virtualDiskNameEv }
			DESCRIPTION
				"Low battery charge level. Logical drive may have lost data."
--#SUMMARY  "[ctl: %d logdrv: %d :] Low battery charge level. Logical drive may have lost data."
--#CATEGORY "Status Events"
--#ARGUMENTS { 0, 1 }
--#SEVERITY MINOR
--#TIMEINDEX 3
--#STATE   OPERATIONAL
--#STATUS  MANDATORY
			::= 915
		pv660fEvent_CTLDEV_IN_CLUSTER TRAP-TYPE
			ENTERPRISE aryMgrEvts
			DESCRIPTION
				"Controller connected to cluster."
--#SUMMARY  "Controller connected to cluster."
--#CATEGORY "IGNORE"
--#ARGUMENTS { }
--#SEVERITY INFORMATIONAL
--#TIMEINDEX 1
--#STATE   OPERATIONAL
--#STATUS  OBSOLETE
			::= 916
		pv660fEvent_CTLDEV_NOT_IN_CLUSTER TRAP-TYPE
			ENTERPRISE aryMgrEvts
			DESCRIPTION
				"Controller disconnected from cluster."
--#SUMMARY  "Controller disconnected from cluster."
--#CATEGORY "IGNORE"
--#ARGUMENTS { }
--#SEVERITY INFORMATIONAL
--#TIMEINDEX 1
--#STATE   OPERATIONAL
--#STATUS  OBSOLETE
			::= 917
		pv660fEvent_CTLDEV_IMPROPERLY_SHUTDOWN TRAP-TYPE
			ENTERPRISE aryMgrEvts
			VARIABLES { controllerNameEv, virtualDiskNameEv }
			DESCRIPTION
				"Controller improperly shutdown! Data may have been lost."
--#SUMMARY  "[ctl: %d logdrv: %d :] Controller improperly shutdown! Data may have been lost"
--#CATEGORY "Status Events"
--#ARGUMENTS { 0, 1 }
--#SEVERITY MINOR
--#TIMEINDEX 3
--#STATE   OPERATIONAL
--#STATUS  MANDATORY
			::= 918
		pv660fEvent_CTLDEV_AUTOMATIC_FLASH_STARTED TRAP-TYPE
			ENTERPRISE aryMgrEvts
			VARIABLES { controllerNameEv }
			DESCRIPTION
				"Dual Active Automatic Flash of Replacement Controller."
--#SUMMARY  "[ctl: %d :] Dual Active Automatic Flash of Replacement Controller."
--#CATEGORY "Status Events"
--#ARGUMENTS { 0 }
--#SEVERITY INFORMATIONAL
--#TIMEINDEX 2
--#STATE   OPERATIONAL
--#STATUS  MANDATORY
			::= 919
		pv660fEvent_CTLDEV_NEGOTIATION_FAILED_JUMPERS TRAP-TYPE
			ENTERPRISE aryMgrEvts
			VARIABLES { controllerNameEv }
			DESCRIPTION
				"Dual Active Negotiation failed jumpers."
--#SUMMARY  "[ctl: %d :] Dual Active Negotiation failed jumpers."
--#CATEGORY "Error Events"
--#ARGUMENTS { 0 }
--#SEVERITY CRITICAL
--#TIMEINDEX 2
--#STATE   NONOPERATIONAL
--#STATUS  MANDATORY
			::= 920
		pv660fEvent_CTLDEV_NEGOTIATION_SAME_ID TRAP-TYPE
			ENTERPRISE aryMgrEvts
			VARIABLES { controllerNameEv }
			DESCRIPTION
				"Dual Active Negotiation failed ID's."
--#SUMMARY  "[ctl: %d :] Dual Active Negotiation failed ID's."
--#CATEGORY "Error Events"
--#ARGUMENTS { 0 }
--#SEVERITY CRITICAL
--#TIMEINDEX 2
--#STATE   NONOPERATIONAL
--#STATUS  MANDATORY
			::= 921
		pv660fEvent_CTLDEV_NEGOTIATION_BOARD_TYPE TRAP-TYPE
			ENTERPRISE aryMgrEvts
			VARIABLES { controllerNameEv }
			DESCRIPTION
				"Dual Active Negotiation failed board types."
--#SUMMARY  "[ctl: %d :] Dual Active Negotiation failed board types."
--#CATEGORY "Error Events"
--#ARGUMENTS { 0 }
--#SEVERITY CRITICAL
--#TIMEINDEX 2
--#STATE   NONOPERATIONAL
--#STATUS  MANDATORY
			::= 922
		pv660fEvent_CTLDEV_NEGOTIATION_DISK_CHANNELS TRAP-TYPE
			ENTERPRISE aryMgrEvts
			VARIABLES { controllerNameEv }
			DESCRIPTION
				"Dual Active Negotiation failed disk channels."
--#SUMMARY  "[ctl: %d :] Dual Active Negotiation failed disk channels."
--#CATEGORY "Error Events"
--#ARGUMENTS { 0 }
--#SEVERITY CRITICAL
--#TIMEINDEX 2
--#STATE   NONOPERATIONAL
--#STATUS  MANDATORY
			::= 923
		pv660fEvent_CTLDEV_NEGOTIATION_HOST_CHANNELS TRAP-TYPE
			ENTERPRISE aryMgrEvts
			VARIABLES { controllerNameEv }
			DESCRIPTION
				"Dual Active Negotiation failed host ports."
--#SUMMARY  "[ctl: %d :] Dual Active Negotiation failed host ports."
--#CATEGORY "Error Events"
--#ARGUMENTS { 0 }
--#SEVERITY CRITICAL
--#TIMEINDEX 2
--#STATE   NONOPERATIONAL
--#STATUS  MANDATORY
			::= 924
		pv660fEvent_CTLDEV_NEGOTIATION_MEMORY_SIZE TRAP-TYPE
			ENTERPRISE aryMgrEvts
			VARIABLES { controllerNameEv }
			DESCRIPTION
				"Dual Active Negotiation failed memory size."
--#SUMMARY  "[ctl: %d :] Dual Active Negotiation failed memory size."
--#CATEGORY "Error Events"
--#ARGUMENTS { 0 }
--#SEVERITY CRITICAL
--#TIMEINDEX 2
--#STATE   NONOPERATIONAL
--#STATUS  MANDATORY
			::= 925
		pv660fEvent_CTLDEV_NEGOTIATION_CACHE_SIZE TRAP-TYPE
			ENTERPRISE aryMgrEvts
			VARIABLES { controllerNameEv }
			DESCRIPTION
				"Dual Active Negotiation failed cache memory size."
--#SUMMARY  "[ctl: %d :] Dual Active Negotiation failed cache memory size."
--#CATEGORY "Error Events"
--#ARGUMENTS { 0 }
--#SEVERITY CRITICAL
--#TIMEINDEX 2
--#STATE   NONOPERATIONAL
--#STATUS  MANDATORY
			::= 926
		pv660fEvent_PHYSDEV_HOT_SPARE_SMALLER TRAP-TYPE
			ENTERPRISE aryMgrEvts
			VARIABLES { controllerNameEv, channelNumberEv, targetIDEv }
			DESCRIPTION
				"Hot spare replaced with a smaller capacity drive."
--#SUMMARY  "[ctl: %d chn: %d tgt: %d :] Hot spare replaced with a smaller capacity drive."
--#CATEGORY "Status Events"
--#ARGUMENTS {0, 1, 2 }
--#SEVERITY INFORMATIONAL
--#TIMEINDEX 4
--#STATE   OPERATIONAL
--#STATUS  MANDATORY
			::= 927
		pv660fEvent_SES_ERR TRAP-TYPE
			ENTERPRISE aryMgrEvts
			VARIABLES { controllerNameEv }
			DESCRIPTION
				"Controller failed, SES not operational.
				This trap is similar to 981 but may occur for older firmware versions."
--#SUMMARY  "[ctl: %d :] Controller failed, SES not operational."
--#CATEGORY "Error Events"
--#ARGUMENTS { 0 }
--#SEVERITY CRITICAL
--#TIMEINDEX 2
--#STATE   OPERATIONAL
--#STATUS  MANDATORY
			::= 980
		pv660fEvent_ENC_SES_ERR TRAP-TYPE
			ENTERPRISE aryMgrEvts
			VARIABLES { controllerNameEv }
			DESCRIPTION
				"Unable to get enclosure status. Doing a PV660F Subsystem rescan may resolve this problem.
				This trap is similar to 980 but may occur for more recent firmware versions."
--#SUMMARY  "[ctl: %d :] Unable to get enclosure status. Doing a PV660F Subsystem rescan may resolve this problem."
--#CATEGORY "Error Events"
--#ARGUMENTS { 0 }
--#SEVERITY MAJOR
--#TIMEINDEX 2
--#STATE   OPERATIONAL
--#STATUS  MANDATORY
			::= 981
		fsysPro_DISK_CAPACITY_WARNING TRAP-TYPE
			ENTERPRISE aryMgrEvts
			VARIABLES { volumeNameEv }
			DESCRIPTION
				"Free disk space has reached warning threshold on volume %s."
--#SUMMARY  "Free disk space has reached warning threshold on volume %s."
--#CATEGORY "Status Events"
--#ARGUMENTS { 0 }
--#SEVERITY INFORMATIONAL
--#STATE   OPERATIONAL
--#STATUS  MANDATORY
			::= 10804
		fsysPro_DISK_CAPACITY_ERROR TRAP-TYPE
			ENTERPRISE aryMgrEvts
			VARIABLES { volumeNameEv }
			DESCRIPTION
				"Free disk space has reached error threshold on volume %s."
--#SUMMARY  "Free disk space has reached error threshold on volume %s."
--#CATEGORY "Error Events"
--#ARGUMENTS { 0 }
--#SEVERITY CRITICAL
--#STATE   OPERATIONAL
--#STATUS  MANDATORY
			::= 10805

	END
