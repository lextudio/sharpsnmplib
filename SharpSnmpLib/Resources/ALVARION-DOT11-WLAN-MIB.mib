-- Title:   ALVARION Private MIB
--       This Private MIB supports BreezeAccessVL product line.
--
--
-- Version:  1.0.23
-- Date:    Thursday May 15 2003
-- Comments:  ALVARION agents also support the following Public MIBs:

-- Some MIB compilers require that the following lines
-- for proper compilation

--#include "rfc1155.smi"
--#include "rfc1212.smi"


-- mgmt      OBJECT IDENTIFIER ::= { iso org(3) dod(6) internet(1) mgmt(2) }
-- mib      OBJECT IDENTIFIER ::= { mgmt 1 }
-- directory   OBJECT IDENTIFIER ::= { internet 1 }
-- experimental  OBJECT IDENTIFIER ::= { internet 3 }
-- private    OBJECT IDENTIFIER ::= { internet 4 }
-- enterprises  OBJECT IDENTIFIER ::= { private 1 }

-- End of lines which might be needed to other MIB browsers
-- for proper compilation


ALVARION-DOT11-WLAN-MIB DEFINITIONS ::= BEGIN


 IMPORTS
    MODULE-IDENTITY, enterprises, IpAddress,Counter32,OBJECT-TYPE
        FROM SNMPv2-SMI
    TRAP-TYPE
        FROM RFC-1215;

 MacAddress ::= OCTET STRING (SIZE(6))
 DisplayString ::= OCTET STRING

 alvarion      OBJECT IDENTIFIER ::= { enterprises 12394 }
 products      OBJECT IDENTIFIER ::= { alvarion 1 }


breezeAccessVLMib MODULE-IDENTITY
  LAST-UPDATED "0106041040Z"
  ORGANIZATION "Alvarion, Ltd."
  CONTACT-INFO " Leana Migdal
            Postal: Alvarion, LTD
      HaBarzel 21a 69710
      ISRAEL
    Tel:  972-3-7674554
    Fax:  972-3-6498875
    E-mail: Leana.Migdal@alvarion.com
    co-authors: Klara Milman"

  DESCRIPTION
    "breeze Access VL MIB Definitions - Release 1.0"
--  REVISION  "24062002000"
--  DESCRIPTION
  ::= { products 1 }

alvarionOID   OBJECT IDENTIFIER ::= { alvarion   4 }
brzAccessVLOID OBJECT IDENTIFIER ::= { alvarionOID  1 }
brzAccessVLAU  OBJECT IDENTIFIER ::= { brzAccessVLOID 1 }
brzAccessVLSU  OBJECT IDENTIFIER ::= { brzAccessVLOID 2 }

brzAccessVLProducts   OBJECT IDENTIFIER ::= { brzAccessVLOID 3 }

-- ****************************************************************************************
-- ****************************************************************************************
-- General System Info
-- ===================
brzaccVLSysInfo    OBJECT IDENTIFIER ::= {breezeAccessVLMib 1}


  brzaccVLUnitHwVersion OBJECT-TYPE
      SYNTAX DisplayString (SIZE(0..32))
      MAX-ACCESS read-only
      STATUS current
      DESCRIPTION
      "Applicable to AU and SU. Read-only.
       Hardware platform version."
      ::= { brzaccVLSysInfo 1 }

  brzaccVLRunningSoftwareVersion OBJECT-TYPE
      SYNTAX DisplayString (SIZE(0..32))
      MAX-ACCESS read-only
      STATUS current
      DESCRIPTION
      "Applicable to AU and SU. Read-only.
       Running software version."
      ::= { brzaccVLSysInfo 2 }

  brzaccVLRunningFrom OBJECT-TYPE
      SYNTAX INTEGER { mainVersion(1) , shadowVersion(2)}
      MAX-ACCESS read-only
      STATUS current
      DESCRIPTION
      "Applicable to AU and SU. Read-only.
       The memory (main or shadow) from which the current version is running from"
      ::= { brzaccVLSysInfo 3 }

  brzaccVLMainVersionNumber OBJECT-TYPE
      SYNTAX DisplayString (SIZE(0..32))
      MAX-ACCESS read-only
      STATUS current
      DESCRIPTION
      "Applicable to AU and SU. Read-only.
       Main software version number."
      ::= { brzaccVLSysInfo 4 }

  brzaccVLMainVersionFileName OBJECT-TYPE
      SYNTAX DisplayString (SIZE(0..32))
      MAX-ACCESS read-only
      STATUS current
      DESCRIPTION
      "Applicable to AU and SU. Read-only.
       Main software version file name."
      ::= { brzaccVLSysInfo 5 }


  brzaccVLShadowVersionNumber OBJECT-TYPE
      SYNTAX DisplayString (SIZE(0..32))
      MAX-ACCESS read-only
      STATUS current
      DESCRIPTION
      "Applicable to AU and SU. Read-only.
       Shadow software version number."
      ::= { brzaccVLSysInfo 6 }

  brzaccVLShadowVersionFileName OBJECT-TYPE
      SYNTAX DisplayString (SIZE(0..32))
      MAX-ACCESS read-only
      STATUS current
      DESCRIPTION
      "Applicable to AU and SU. Read-only.
       Shadow software version file name."
      ::= { brzaccVLSysInfo 7 }

  brzaccVLUnitMacAddress OBJECT-TYPE
      SYNTAX MacAddress
      MAX-ACCESS read-only
      STATUS current
      DESCRIPTION
      "Applicable to AU and SU. Read-only.
       Unit hardware MAC address."
      ::= { brzaccVLSysInfo 8 }

  brzaccVLUnitType OBJECT-TYPE
      SYNTAX INTEGER {auBS (1), auNI(2) , su6(3),su24(4) }
      MAX-ACCESS read-only
      STATUS current
      DESCRIPTION
      "Applicable to AU and SU. Read-only.
       auBS (1)  : AU-BS (modular access unit),
       auNI (2)  : AU-NI (stand-alone access unit),
       su6 (3) : SU-6 (subscriber unit supporting 6 Mbps) or
       su24(4) : SU-24 (subscriber unit supporting 24 Mbps)."
       ::= { brzaccVLSysInfo 9 }

  brzaccVLAssociatedAU OBJECT-TYPE
      SYNTAX MacAddress
      MAX-ACCESS read-only
      STATUS current
      DESCRIPTION
      "Applicable to SU only. Read-only.
       Associated AU MAC address."
      ::= { brzaccVLSysInfo 10 }

  brzaccVLNumOfAssociationsSinceLastReset OBJECT-TYPE
      SYNTAX INTEGER
      MAX-ACCESS read-only
      STATUS current
      DESCRIPTION
      "Applicable to AU and SU. Read-only.
       The number of associations since last reset, including
       duplicate associations (re-associations)."
      ::= { brzaccVLSysInfo 11 }


  brzaccVLCurrentNumOfAssociations OBJECT-TYPE
      SYNTAX INTEGER
      MAX-ACCESS read-only
      STATUS current
      DESCRIPTION
      "Applicable to AU only. Read-only.
       The number of subscriber units currently associated with
       the AU."
      ::= { brzaccVLSysInfo 13 }

  brzaccVLUnitBootVersion OBJECT-TYPE
      SYNTAX DisplayString (SIZE(0..32))
      MAX-ACCESS read-only
      STATUS current
      DESCRIPTION
      "Applicable to AU and SU. Read-only.
       Boot version."
      ::= { brzaccVLSysInfo 14 }

  brzaccVLRadioBand OBJECT-TYPE
      SYNTAX INTEGER {band_5_7Ghz (1), band_5_4GHz (2)}
      MAX-ACCESS read-only
      STATUS current
      DESCRIPTION
      "Applicable to AU and SU. Read-only.
       The unit's radio band."
      ::= { brzaccVLSysInfo 15 }

  brzaccVLCurrentEthernetPortState OBJECT-TYPE
      SYNTAX INTEGER { halfDuplexAnd10Mbps (1),
               fullDuplexAnd10Mbps (2),
               halfDuplexAnd100Mbps (3),
               fullDuplexAnd100Mbps (4),
               linkDown       (5) }

      MAX-ACCESS read-only
      STATUS current
      DESCRIPTION
      "Applicable to AU and SU. Read-only.
       The current Ethernet port state."
      ::= { brzaccVLSysInfo 16 }



-- Unit Control
-- ============
brzaccVLUnitControl    OBJECT IDENTIFIER ::= {breezeAccessVLMib 2}

  brzaccVLResetUnit OBJECT-TYPE
      SYNTAX INTEGER { cancel (1), resetSystemNow (2) }
      MAX-ACCESS read-write
      STATUS current
      DESCRIPTION
      "Applicable to AU and SU.
       Resets the unit and applies new parameter values."
      ::= { brzaccVLUnitControl 1 }

  brzaccVLSetDefaults OBJECT-TYPE
      SYNTAX INTEGER { completeFactory (1), partialFactory (2), completeOperator (3), partialOperator (4), cancel(5) }
      MAX-ACCESS read-write
      STATUS current
      DESCRIPTION
      "Applicable to AU and SU.
       Sets unit configuration to Defaults values after the
       next reset.
       completeFactory : All parameters revert to Factory
                Defaults values.
       partialFactory : All parameters revert to Factory
                Defaults values, except the parameters
                required for maintaining wireless
                connectivity.
       completeOperator: All parameters revert to Operator
                Defaults values.
       partialOperator : All parameters revert to Operator
                Defaults values, except the parameters
                required for maintaining wireless
                connectivity."
      ::= { brzaccVLUnitControl 2 }

  brzaccVLUnitName OBJECT-TYPE
      SYNTAX DisplayString (SIZE(32))
      MAX-ACCESS read-write
      STATUS current
      DESCRIPTION
      "Applicable to AU and SU.
       The unit name.
       A string of up to 32 printable ASCII characters."
      ::= { brzaccVLUnitControl 3 }


  brzaccVLFlashMemoryControl OBJECT-TYPE
      SYNTAX INTEGER { resetAndBootFromShadowVersion (1),
               useCurrentVersionAfterReset (2),cancel(3) }
      MAX-ACCESS read-write
      STATUS current
      DESCRIPTION
      "Applicable to AU and SU.
       resetAndBootFromShadowVersion : Activates the backup
                       version.
       useCurrentVersionAfterReset  : The currently active
                       version will become the main
                       version and will be activated
                       after next reset."
      ::= { brzaccVLUnitControl 4 }


  brzaccVLTelnetLogoutTimer OBJECT-TYPE
      SYNTAX INTEGER
      MAX-ACCESS read-write
      STATUS current
      DESCRIPTION
      "Applicable to AU and SU.
       Time-out of management via Telnet program.
       Automatic exit if the program is inactive for the
       defined time.
       Range: 1 to 999 (minutes)."
      ::= { brzaccVLUnitControl 5 }

  brzaccVLSaveCurrentConfigurationAsOperatorDefaults OBJECT-TYPE
      SYNTAX INTEGER { saveAsDefaults (1),cancel(2) }
      MAX-ACCESS read-write
      STATUS current
      DESCRIPTION
      "Applicable to AU and SU.
       Saves the current configuration as Operator Defaults."
      ::= { brzaccVLUnitControl 6 }

  brzaccVLExitTelnet OBJECT-TYPE
      SYNTAX INTEGER { cancelOperation (1), exit (2)}
      MAX-ACCESS read-write
      STATUS current
      DESCRIPTION
      "Applicable to AU and SU.
       Exit the management via Telnet program."
      ::= { brzaccVLUnitControl 7 }

brzaccVLUnitPasswords   OBJECT IDENTIFIER ::= {brzaccVLUnitControl 8}

  brzaccVLReadOnlyPassword OBJECT-TYPE
      SYNTAX DisplayString (SIZE(8))
      MAX-ACCESS read-write
      STATUS current
      DESCRIPTION
      "Applicable to AU and SU.
       The User (read only) password.
       Up to 8 printable ASCII characters."
      ::= { brzaccVLUnitPasswords 1 }

  brzaccVLInstallerPassword OBJECT-TYPE
      SYNTAX DisplayString (SIZE(8))
      MAX-ACCESS read-write
      STATUS current
      DESCRIPTION
      "Applicable to AU and SU.
       The Installer password.
       Up to 8 printable ASCII characters."
      ::= { brzaccVLUnitPasswords 2 }

  brzaccVLAdminPassword OBJECT-TYPE
      SYNTAX DisplayString (SIZE(8))
      MAX-ACCESS read-write
      STATUS current
      DESCRIPTION
      "Applicable to AU and SU.
       The Administrator password. This is also the Write
       Community String.
       Up to 8 printable ASCII characters."
      ::= { brzaccVLUnitPasswords 3 }


  brzaccVLEthernetNegotiationMode OBJECT-TYPE
      SYNTAX INTEGER { force10MbpsAndHalfDuplex  (1),
               force10MbpsAndFullDuplex  (2),
               force100MbpsAndHalfDuplex (3),
               force100_MbpsAndFullDuplex (4),
               autoNegotiationMode    (5) }
      MAX-ACCESS read-write
      STATUS current
      DESCRIPTION
      "Applicable to AU and SU.
       The speed/duplex mode of the Ethernet port."
      ::= { brzaccVLUnitControl 9 }

brzaccVLFTPParameters   OBJECT IDENTIFIER ::= {brzaccVLUnitControl 10}

brzaccVLFTPServerParams   OBJECT IDENTIFIER ::= {brzaccVLFTPParameters 1}

  brzaccVLFTPServerUserName OBJECT-TYPE
      SYNTAX DisplayString (SIZE(18))
      MAX-ACCESS read-write
      STATUS current
      DESCRIPTION
      "Applicable to AU and SU.
       The user name to be used for access to the FTP server. "
      ::= { brzaccVLFTPServerParams 1 }

  brzaccVLFTPServerPassword OBJECT-TYPE
      SYNTAX DisplayString (SIZE(18))
      MAX-ACCESS read-write
      STATUS current
      DESCRIPTION
      "Applicable to AU and SU.
       The password to be used for access to the FTP server."
      ::= { brzaccVLFTPServerParams 2 }

  brzaccVLFTPClientIPAddress OBJECT-TYPE
      SYNTAX IpAddress
      MAX-ACCESS read-write
      STATUS current
      DESCRIPTION
      "Applicable to AU and SU.
       The IP address of the FTP stack in the unit."
      ::= { brzaccVLFTPServerParams 3 }

  brzaccVLFTPHostIpAddress OBJECT-TYPE
      SYNTAX IpAddress
      MAX-ACCESS read-write
      STATUS current
      DESCRIPTION
      "Applicable to AU and SU.
       The IP address of the FTP server."
      ::= { brzaccVLFTPServerParams 4 }



brzaccVLFTPSwDownload   OBJECT IDENTIFIER ::= {brzaccVLFTPParameters 2}

  brzaccVLFTPSwFileName OBJECT-TYPE
      SYNTAX DisplayString (SIZE(20))
      MAX-ACCESS read-write
      STATUS current
      DESCRIPTION
      "Applicable to AU and SU.
       The name of the SW file to be downloaded."
      ::= { brzaccVLFTPSwDownload 1 }

  brzaccVLFTPSwSourceDir OBJECT-TYPE
      SYNTAX DisplayString (SIZE(80))
      MAX-ACCESS read-write
      STATUS current
      DESCRIPTION
      "Applicable to AU and SU.
       The source directory of the required file in the FTP server.
       Up to 80 printable ASCII characters.
       Use dot (.) To clear field"
      ::= { brzaccVLFTPSwDownload 2 }

  brzaccVLFTPDownloadSwFile OBJECT-TYPE
      SYNTAX INTEGER { downloadFile (1) , cancel (2)}
      MAX-ACCESS read-write
      STATUS current
      DESCRIPTION
      "Applicable to AU and SU.
       Execution of the SW download operation"
      ::= { brzaccVLFTPSwDownload 3 }

brzaccVLConfigurationFileLoading   OBJECT IDENTIFIER ::= {brzaccVLFTPParameters 3}

  brzaccVLConfigurationFileName OBJECT-TYPE
      SYNTAX DisplayString (SIZE(20))
      MAX-ACCESS read-write
      STATUS current
      DESCRIPTION
      "Applicable to AU and SU.
       The name of the configuration file to be downloaded/uploaded."
      ::= { brzaccVLConfigurationFileLoading 1 }



  brzaccVLOperatorDefaultsFileName OBJECT-TYPE
      SYNTAX DisplayString (SIZE(20))
      MAX-ACCESS read-write
      STATUS current
      DESCRIPTION
      "Applicable to AU and SU.
       The name of the Operator Defaults file to be downloaded/uploaded"
      ::= { brzaccVLConfigurationFileLoading 2 }

  brzaccVLFTPConfigurationFileSourceDir OBJECT-TYPE
      SYNTAX DisplayString (SIZE(80))
      MAX-ACCESS read-write
      STATUS current
      DESCRIPTION
      "Applicable to AU and SU.
       The source directory of the required file in the FTP server.
       Up to 80 printable ASCII characters.
       Use dot (.) To clear field"
      ::= { brzaccVLConfigurationFileLoading 3 }

  brzaccVLExecuteFTPConfigurationFileLoading OBJECT-TYPE
      SYNTAX INTEGER {executeFTPGetConfigurationFile (1), executeFTPPutConfigurationFile (2),
               executeFTPGetOperatorDefaults (3) , executeFTPPutOperatorDefaults (4), cancel (5) }
      MAX-ACCESS read-write
      STATUS current
      DESCRIPTION
      "Applicable to AU and SU.
       Execution of the file download/upload operation."
      ::= { brzaccVLConfigurationFileLoading 4 }



  brzaccVLLoadingStatus OBJECT-TYPE
      SYNTAX INTEGER {inProcess (1), successful (2), failed (3)}
      MAX-ACCESS read-only
      STATUS current
      DESCRIPTION
      "Applicable to AU and SU.
       The status of the last loading operation."
      ::= { brzaccVLUnitControl 11 }



-- Network Management Params
-- =========================
  brzaccVLNwMngParameters  OBJECT IDENTIFIER ::= {breezeAccessVLMib 3}

  brzaccVLAccessToNwMng OBJECT-TYPE
      SYNTAX  INTEGER { fromWirelessOnly (1),
               fromEthernetOnly (2),
               fromBothWirelessAndEthernet (3),
               na (255) }
      MAX-ACCESS read-write
      STATUS current
      DESCRIPTION
      "Applicable to AU and SU.
       The port to be used for remote management."
      ::= { brzaccVLNwMngParameters 1 }


  brzaccVLNwMngFilter OBJECT-TYPE
       SYNTAX INTEGER { disable (1),
               activateOnEthernetPort (2),
               activateOnWirelessPort (3),
               activateOnBothWirelessAndEthernet (4),
               na (255) }
      MAX-ACCESS read-write
      STATUS current
      DESCRIPTION
      "Applicable to AU and SU.
       Disables or enable on one of the ports, or on both
       ports, IP address based filtering of management messages
       (e.g. SNMP , Telnet , TFTP , DHCP)."
      ::= { brzaccVLNwMngParameters 2 }




  mngIpFilterTable OBJECT-TYPE
      SYNTAX SEQUENCE OF MngIpFilterEntry
      MAX-ACCESS not-accessible
      STATUS current
      DESCRIPTION
        "Applicable to AU and SU.
        A Management IP Filter Table of up to 3 IP addresses
        of devices that are authorized to access the unit
        for management purposes."
      ::= { brzaccVLNwMngParameters 3 }

  mngIpFilterEntry OBJECT-TYPE
      SYNTAX MngIpFilterEntry
      MAX-ACCESS not-accessible
      STATUS current
      DESCRIPTION
        "Applicable to AU and SU.
        A Management IP Filter Table entry."
      INDEX { brzaccVLNwMngIpTableIdx }
      ::= { mngIpFilterTable 1 }

  MngIpFilterEntry ::= SEQUENCE { brzaccVLNwMngIpAddress  IpAddress,
                  brzaccVLNwMngIpTableIdx INTEGER }

  brzaccVLNwMngIpAddress  OBJECT-TYPE
      SYNTAX IpAddress
      MAX-ACCESS read-write
      STATUS current
      DESCRIPTION
      "Applicable to AU and SU.
       An IP address in the Management IP Filter Table."
     ::= { mngIpFilterEntry 1 }

  brzaccVLNwMngIpTableIdx  OBJECT-TYPE
      SYNTAX INTEGER
      MAX-ACCESS read-only
      STATUS current
      DESCRIPTION
      "Applicable to AU and SU.
       A table index for an entry in the Management IP Filter
       Table."
     ::= { mngIpFilterEntry 2 }


  brzaccVLDeleteOneNwIpAddr OBJECT-TYPE
      SYNTAX INTEGER { deleteFirstEntry (1),
               deleteSecondEntry (2),
               deleteThirdEntry (3),
               cancelOperation (4),
               na (255)
              }
      MAX-ACCESS read-write
      STATUS current
      DESCRIPTION
      "Applicable to AU and SU.
       Deletes a single selected entry from the Management IP
       Filter Table."
      ::= { brzaccVLNwMngParameters 4 }

  brzaccVLDeleteAllNwIpAddrs OBJECT-TYPE
      SYNTAX INTEGER { deleteAll (1), cancelOperation (2), na (255) }
      MAX-ACCESS read-write
      STATUS current
      DESCRIPTION
      "Applicable to AU and SU.
       Deletes all entries from the Management IP Filter Table."
      ::= { brzaccVLNwMngParameters 5 }

  brzaccVLAccessToNwTrap OBJECT-TYPE
      SYNTAX INTEGER { disable(1), enable(2) }
      MAX-ACCESS read-write
      STATUS current
      DESCRIPTION
      "Applicable to AU and SU.
       Enables or disables sending of traps."
      ::= { brzaccVLNwMngParameters 6 }

  mngTrapTable OBJECT-TYPE
      SYNTAX SEQUENCE OF MngTrapEntry
      MAX-ACCESS not-accessible
      STATUS current
      DESCRIPTION
      "Applicable to AU and SU.
       A Management Trap Table of up to 3 IP addresses of
       stations to send traps to."
      ::= { brzaccVLNwMngParameters 7 }

  mngTrapEntry OBJECT-TYPE
      SYNTAX MngTrapEntry
      MAX-ACCESS not-accessible
      STATUS current
      DESCRIPTION
      "Applicable to AU and SU.
       A Management Trap Table entry."
      INDEX { brzaccVLNwTrapTableIdx }
      ::= { mngTrapTable 1 }

  MngTrapEntry ::= SEQUENCE { brzaccVLNwMngTrapCommunity DisplayString,
                brzaccVLNwMngTrapAddress  IpAddress,
                brzaccVLNwTrapTableIdx   INTEGER }

  brzaccVLNwMngTrapCommunity OBJECT-TYPE
      SYNTAX DisplayString (SIZE(14))
      MAX-ACCESS read-write
      STATUS current
      DESCRIPTION
      "Applicable to AU and SU.
       The trap community associated with the applicable
       entry in the Management Trap Table.
       Up to 14 printable case sensitive ASCII characters."
      ::= { mngTrapEntry 1 }

  brzaccVLNwMngTrapAddress  OBJECT-TYPE
      SYNTAX IpAddress
      MAX-ACCESS read-write
      STATUS current
      DESCRIPTION
      "Applicable to AU and SU.
       An IP address in the Management Trap Table entry."
    ::= { mngTrapEntry 2 }

  brzaccVLNwTrapTableIdx  OBJECT-TYPE
      SYNTAX INTEGER
      MAX-ACCESS read-only
      STATUS current
      DESCRIPTION
      "Applicable to AU and SU.
       Tables Index for an entry in the Management Trap Table."
    ::= { mngTrapEntry 3 }

  brzaccVLDeleteOneTrapAddr OBJECT-TYPE
      SYNTAX INTEGER { deletefirstEntry (1),
               deletesecondEntry (2),
               deletethirdEntry (3),
               cancelOperation (4),
               na (255) }

      MAX-ACCESS read-write
      STATUS current
      DESCRIPTION
      "Applicable to AU and SU.
       Deletes a single selected entry from the Management
       Trap Table."
      ::= { brzaccVLNwMngParameters 8 }

  brzaccVLDeleteAllTrapAddrs OBJECT-TYPE
      SYNTAX INTEGER { deleteAll (1),cancelOperation (2), na (255) }
      MAX-ACCESS read-write
      STATUS current
      DESCRIPTION
      "Applicable to AU and SU.
       Deletes all entries from the Management Trap Table."
      ::= { brzaccVLNwMngParameters 9 }

-- IP Params:
-- ===========
brzaccVLIpParams   OBJECT IDENTIFIER ::= {breezeAccessVLMib 4}

  brzaccVLUnitIpAddress OBJECT-TYPE
      SYNTAX IpAddress
      MAX-ACCESS read-write
      STATUS current
      DESCRIPTION
      "Applicable to AU and SU.
       IP address of the unit."
      ::= { brzaccVLIpParams 1 }

  brzaccVLSubNetMask OBJECT-TYPE
      SYNTAX IpAddress
      MAX-ACCESS read-write
      STATUS current
      DESCRIPTION
      "Applicable to AU and SU.
       Subnet mask of the unit."
      ::= { brzaccVLIpParams 2 }

  brzaccVLDefaultGWAddress OBJECT-TYPE
      SYNTAX IpAddress
      MAX-ACCESS read-write
      STATUS current
      DESCRIPTION
      "Applicable to AU and SU.
       Default gateway IP address of the unit."
      ::= { brzaccVLIpParams 3 }

  brzaccVLUseDhcp OBJECT-TYPE
      SYNTAX INTEGER{ disable (1),
               dhcpOnly (2),
               automatic (3) }
      MAX-ACCESS read-write
      STATUS current
      DESCRIPTION
      "Applicable to AU and SU.
       DHCP client mode of operation.
       disabled : Use regular (manual) methods to configure IP
            parameters.
       dHCP Only: Use DHCP server to configure IP parameters.
       automatic: Use DHCP server to configure IP parameters.
            If a DHCP server is not available, use
            manually configured values."
      ::= { brzaccVLIpParams 4 }

  brzaccVLAccessToDHCP OBJECT-TYPE
      SYNTAX INTEGER{ fromWirelessOnly  (1),
               fromEthernetOnly (2),
               fromBothWirelessAndEthernet (3) }
      MAX-ACCESS read-write
      STATUS current
      DESCRIPTION
      "Applicable to AU and SU.
       The port to be used for communicating with a DHCP server."
      ::= { brzaccVLIpParams 5 }

  brzaccVLRunTimeIPaddr OBJECT-TYPE
      SYNTAX IpAddress
      MAX-ACCESS read-only
      STATUS current
      DESCRIPTION
      "Applicable to AU and SU. Read-only.
       The run-time IP address. If DHCP is used the Run Time
       IP Address is the address given to the unit by the
       server. Otherwise it is the manualy configured address."
      ::= { brzaccVLIpParams 6 }

  brzaccVLRunTimeSubNetMask OBJECT-TYPE
      SYNTAX IpAddress
      MAX-ACCESS read-only
      STATUS current
      DESCRIPTION
      "Applicable to AU and SU. Read-only.
       The run-time Subnet Mask. If DHCP is used the Run Time
       Subnet Mask is the mask given to the unit by the server.
       Otherwise it is the manualy configured mask."
      ::= { brzaccVLIpParams 7 }

  brzaccVLRunTimeDefaultIPGateway OBJECT-TYPE
      SYNTAX IpAddress
      MAX-ACCESS read-only
      STATUS current
      DESCRIPTION
      "Applicable to AU and SU. Read-only.
       The run-time Gateway IP address. If DHCP is used the
       Run Time Gateway IP Address is the address given to the
       unit by the server. Otherwise it is the manualy
       configured address."
      ::= { brzaccVLIpParams 8 }


-- Bridge Params
-- ==============
brzaccVLBridgeParameters   OBJECT IDENTIFIER ::= {breezeAccessVLMib 5}


brzaccVLVLANSupport    OBJECT IDENTIFIER ::= {brzaccVLBridgeParameters 1}

  brzaccVLVlanID OBJECT-TYPE
      SYNTAX INTEGER
      MAX-ACCESS read-write
      STATUS current
      DESCRIPTION
      "Applicable to SU only.
       VLAN ID for data frame tagging.
       Applicable to Access Link only.
       Range: 1-4094. 0 - not applicable."
      ::= { brzaccVLVLANSupport 1 }

  brzaccVLEthernetLinkType OBJECT-TYPE
      SYNTAX INTEGER { accessLink (1),
               trunkLink (2),
               hybridLink (3) }
      MAX-ACCESS read-write
      STATUS current
      DESCRIPTION
      "Applicable to AU and SU.
       VLAN support mode (Link Type).
       The Access Link option is not available for AU."
      ::= { brzaccVLVLANSupport 2 }


  brzaccVLManagementVlanID OBJECT-TYPE
      SYNTAX INTEGER
      MAX-ACCESS read-write
      STATUS current
      DESCRIPTION
      "Applicable to AU and SU.
       VLAN ID for management frame tagging.
       Range: 1-4094, 65535 for No VLAN tagging."
      ::= { brzaccVLVLANSupport 3 }



brzaccVLVLANForwarding    OBJECT IDENTIFIER ::= {brzaccVLVLANSupport 4}


   brzaccVLVlanForwardingSupport OBJECT-TYPE
      SYNTAX INTEGER { disable (1) , enable (2), na(255) }
      MAX-ACCESS read-write
      STATUS current
      DESCRIPTION
      "Applicable to AU and SU.
       Enables or disables the VLAN forwarding feature.
       (applicable in Trunk links only)."
      ::= { brzaccVLVLANForwarding 1 }



  brzaccVLVlanForwardingTable OBJECT-TYPE
      SYNTAX SEQUENCE OF BrzaccVLVlanForwardingEntry
      MAX-ACCESS not-accessible
      STATUS current
      DESCRIPTION
      "Applicable to AU and SU.
       A VLAN Forwarding Table of up to 20 VLAN IDs of devices
       to which data frames are forwarded when VLAN Forwarding
       is Enabled. (applicable in Trunk links only).
       Not accessible."
      ::= { brzaccVLVLANForwarding 2 }

  brzaccVLVlanForwardingEntry OBJECT-TYPE
      SYNTAX BrzaccVLVlanForwardingEntry
      MAX-ACCESS not-accessible
      STATUS current
      DESCRIPTION
      "Applicable to AU and SU.
       A VLAN Forwarding Table entry. (applicable in Trunk
       links only).
       Not accessible."
      INDEX { brzaccVLVlanForwardingTableIdx }
      ::= { brzaccVLVlanForwardingTable 1 }

  BrzaccVLVlanForwardingEntry ::= SEQUENCE {
      brzaccVLVlanForwardingTableIdx INTEGER,
      brzaccVLVlanIdForwarding INTEGER
      }


  brzaccVLVlanForwardingTableIdx  OBJECT-TYPE
      SYNTAX INTEGER
      MAX-ACCESS read-only
      STATUS current
      DESCRIPTION
      "Applicable to AU and SU.
       A read only table index for a VLAN entry in the VLAN
       Forwarding Table."
    ::= { brzaccVLVlanForwardingEntry 1 }

  brzaccVLVlanIdForwarding  OBJECT-TYPE
      SYNTAX INTEGER
      MAX-ACCESS read-write
      STATUS current
      DESCRIPTION
      "Applicable to AU and SU.
       The list of VLAN ID's in the VLAN ID Forwarding Table.
       To Remove a VLAN ID - SET the corresponding entry to 0.
       To Add a new VLAN ID SET an entry which is currently 0."
    ::= { brzaccVLVlanForwardingEntry 2 }



brzaccVLVlanRelaying  OBJECT IDENTIFIER ::= {brzaccVLVLANSupport 5}


  brzaccVLVlanRelayingSupport OBJECT-TYPE
      SYNTAX INTEGER { disable (1) , enable (2), na(255) }
      MAX-ACCESS read-write
      STATUS current
      DESCRIPTION
      "Applicable to AU only.
       Enables or disables VLAN Relaying (applicable in
       Trunk links only)."
      ::= { brzaccVLVlanRelaying 1 }

  brzaccVLVlanRelayingTable OBJECT-TYPE
      SYNTAX SEQUENCE OF BrzaccVLVlanRelayingEntry
      MAX-ACCESS not-accessible
      STATUS current
      DESCRIPTION
      "Applicable to AU only.
       A VLAN Relaying Table of up to 20 VLAN IDs of devices
       to which data frames are relayed when VLAN Relaying is
       Enabled. (applicable in Trunk links only).
       Not accessible."
      ::= { brzaccVLVlanRelaying 2 }

  brzaccVLVlanRelayingEntry OBJECT-TYPE
      SYNTAX BrzaccVLVlanRelayingEntry
      MAX-ACCESS not-accessible
      STATUS current
      DESCRIPTION
      "Applicable to AU only.
       A VLAN Relaying Table entry. (applicable in Trunk links
       only).
       Not accessible."
      INDEX { brzaccVLVlanRelayingTableIdx }
      ::= { brzaccVLVlanRelayingTable 1 }

  BrzaccVLVlanRelayingEntry ::= SEQUENCE {
      brzaccVLVlanRelayingTableIdx INTEGER,
      brzaccVLVlanIdRelaying INTEGER
      }


  brzaccVLVlanRelayingTableIdx  OBJECT-TYPE
      SYNTAX INTEGER
      MAX-ACCESS read-only
      STATUS current
      DESCRIPTION
      "Applicable to AU only.
       A read only table index for a VLAN entry in the VLAN
       Relaying Table."
    ::= { brzaccVLVlanRelayingEntry 1 }


  brzaccVLVlanIdRelaying  OBJECT-TYPE
      SYNTAX INTEGER
      MAX-ACCESS read-write
      STATUS current
      DESCRIPTION
      "Applicable to AU only.
       The list of VLAN ID's in the VLAN ID Relaying Table.
       To Remove a VLAN ID - SET the corresponding entry to 0.
       To Add a new VLAN ID SET an entry which is currently 0.
       Range: 0-4094 , 0 - remove entry."
    ::= { brzaccVLVlanRelayingEntry 2 }


brzaccVLVLANTrafficPriority    OBJECT IDENTIFIER ::= {brzaccVLVLANSupport 6}

  brzaccVLVlanDataPriority OBJECT-TYPE
      SYNTAX INTEGER { na(255) }
      MAX-ACCESS read-write
      STATUS current
      DESCRIPTION
      "Applicable to SU only.
       Priority tagging for data frames. Applicable to Access
       Link only.
       Range: 0 to 7."
      ::= { brzaccVLVLANTrafficPriority 1 }


  brzaccVLVlanManagementPriority OBJECT-TYPE
      SYNTAX INTEGER { na(255) }
      MAX-ACCESS read-write
      STATUS current
      DESCRIPTION
      "Applicable to AU and SU.
       Priority tagging for management frames. Applicable to
       Access Link and Trunk Link only.
       Range: 0-7."
      ::= { brzaccVLVLANTrafficPriority 2 }


  brzaccVLVlanPriorityThreshold OBJECT-TYPE
      SYNTAX INTEGER { na(255) }
      MAX-ACCESS read-write
      STATUS current
      DESCRIPTION
      "Applicable to AU and SU.
       Priority threshold for tagged frames received from
       Ethernet port. Applicable to Hybrid Link and Trunk Link
       only.
       Valid values: 0-7."
      ::= { brzaccVLVLANTrafficPriority 3 }

  brzaccVLBridgeAgingTime OBJECT-TYPE
      SYNTAX INTEGER
      MAX-ACCESS read-write
      STATUS current
      DESCRIPTION
      "Applicable to AU and SU.
       Bridge aging time for devices on both the Ethernet and
       wireless link sides.
       Range: 20 to 2000 seconds."
      ::= { brzaccVLBridgeParameters 2 }


  brzaccVLBroadcastRelaying OBJECT-TYPE
      SYNTAX INTEGER { disable(1), enable(2), na (255) }
      MAX-ACCESS read-write
      STATUS current
      DESCRIPTION
      "Applicable to AU only.
      Enables/disables the relaying of broadcast messages to
      the wireless link."
      ::= { brzaccVLBridgeParameters 4 }

  brzaccVLUnicastRelaying OBJECT-TYPE
      SYNTAX INTEGER { disable(1), enable(2), na (255) }
      MAX-ACCESS read-write
      STATUS current
      DESCRIPTION
      "Applicable to AU only.
       Enables/disables the relaying of unicast messages to
       the wireless link."
      ::= { brzaccVLBridgeParameters 5 }

  brzaccVLEthBroadcastFiltering OBJECT-TYPE
      SYNTAX INTEGER { disable (1),
               onEthernetOnly (2),
               onWirelessOnly (3),
               onBothWirelessAndEthernet (4),
               na (255) }
      MAX-ACCESS read-write
      STATUS current
      DESCRIPTION
      "Applicable to SU only.
       Enables/disables the filtering of Ethernet (layer2)
       broadcasts.
       disable       : No filtering.
       onEthernetOnly   : Filters broadcasts received on the Ethernet port only.
       onWirelessOnly   : Filters broadcasts received on the Wlan port only.
       onBothWirelessAndEth: Filters broadcasts received on both ports."
      ::= { brzaccVLBridgeParameters 6 }

brzaccVLEthBroadcastingParameters   OBJECT IDENTIFIER ::= {brzaccVLBridgeParameters 7}

  brzaccVLDHCPBroadcastOverrideFilter OBJECT-TYPE
      SYNTAX INTEGER { disable (1), enable (2), na (255) }
      MAX-ACCESS read-write
      STATUS current
      DESCRIPTION
      "Applicable to SU only.
       Enables or disables the broadcasting of DHCP messages,
       overriding the general *brzaccVLEthBroadcastFiltering Ethernet
       broadcast filtering option."
      ::= { brzaccVLEthBroadcastingParameters 1 }

  brzaccVLPPPoEBroadcastOverrideFilter OBJECT-TYPE
      SYNTAX INTEGER { disable (1), enable (2), na (255) }
      MAX-ACCESS read-write
      STATUS current
      DESCRIPTION
      "Applicable to SU only.
       Enables or disables the broadcasting of PPPoE messages,
       overriding the general *brzaccVLEthBroadcastFiltering Ethernet
       broadcast filtering option."
      ::= { brzaccVLEthBroadcastingParameters 2 }

  brzaccVLARPBroadcastOverrideFilter OBJECT-TYPE
      SYNTAX INTEGER { disable (1), enable (2), na (255) }
      MAX-ACCESS read-write
      STATUS current
      DESCRIPTION
      "Applicable to SU only.
       Enables or disables the broadcasting of ARP messages,
       overriding the general *brzaccVLEthBroadcastFiltering Ethernet
       broadcast filtering option."
      ::= { brzaccVLEthBroadcastingParameters 3 }

brzaccVLToSPriorityParameters   OBJECT IDENTIFIER ::= {brzaccVLBridgeParameters 8}


  brzaccVLToSPrecedenceThreshold OBJECT-TYPE
      SYNTAX INTEGER
      MAX-ACCESS read-write
      STATUS current
      DESCRIPTION
      "Applicable to SU and AU only.
       Priority threshold (based on the ToS) for frames received
       from the Ethernet port.
       Range: 0-7."
      ::= { brzaccVLToSPriorityParameters 1 }


-- Air Interface Params
-- =====================
brzaccVLAirInterface   OBJECT IDENTIFIER ::= {breezeAccessVLMib 6}

brzaccVLESSIDParameters   OBJECT IDENTIFIER ::= {brzaccVLAirInterface 1}

  brzaccVLESSID OBJECT-TYPE
      SYNTAX DisplayString (SIZE(31))
      MAX-ACCESS read-write
      STATUS current
      DESCRIPTION
      "Applicable to SU and AU.
       The Extended Service Set ID (ESSID) used to prevent
       the merging of collocated systems.
       The ESSID is accessible only with the write community
       string (administrator password).
       Up to 31 printable case sensitive ASCII characters."
      ::= { brzaccVLESSIDParameters 1 }

  brzaccVLOperatorESSIDOption OBJECT-TYPE
      SYNTAX INTEGER {disable (1) , enable (2), na (255) }
      MAX-ACCESS read-write
      STATUS current
      DESCRIPTION
      "Applicable to AU only.
       Enabling/disabling the use of the Operator ESSID."
      ::= { brzaccVLESSIDParameters 2 }


  brzaccVLOperatorESSID OBJECT-TYPE
      SYNTAX DisplayString (SIZE(31))
      MAX-ACCESS read-write
      STATUS current
      DESCRIPTION
      "Applicable to AU only.
       A secondary ESSID to support easy installation of SUs as well as
       the use of the Best AU feature.
       Accessible only with SNMP Write Community
       Up to 31 printable case sensitive ASCII characters."
      ::= { brzaccVLESSIDParameters 3}

  brzaccVLRunTimeESSID OBJECT-TYPE
      SYNTAX DisplayString (SIZE(31))
      MAX-ACCESS read-only
      STATUS mandatory
      DESCRIPTION
      "Applicable to SU only.
       The ESSID of the associated AU.
       Accessible only with SNMP Write Community.
       Up to 31 printable ASCII characters, case sensitive."
      ::= { brzaccVLESSIDParameters 4 }


  brzaccVLMaximumCellRadius OBJECT-TYPE
      SYNTAX INTEGER { noCompensation (1), upTo3km(2) ,upTo5km(3),upTo10km(4) }
      MAX-ACCESS read-write
      STATUS current
      DESCRIPTION
      "Applicable to AU and SU.
      For SU unit : read only"
      ::= { brzaccVLAirInterface 2 }

  brzaccVLAIFS OBJECT-TYPE
      SYNTAX INTEGER { oneSlot (1), twoSlots (2) }
      MAX-ACCESS read-write
      STATUS current
      DESCRIPTION
      "Applicable to AU and SU.
      Arbitration Inter-Frame Spacing (AIFS) value, in slots."
      ::= { brzaccVLAirInterface 3 }


  brzaccVLWirelessTrapThreshold OBJECT-TYPE
    SYNTAX INTEGER
    MAX-ACCESS read-write
    STATUS current
    DESCRIPTION
    "Applicable to AU only.
     A wireless link quality threshold, expressed in % of retransmissions,
     for sending the brzaccVLAUWirelessQualityTRAP.
     This trap indicate whether the quality has gone below or
     above the specified threshold.
     The Threshold Range: 1-100 (% retransmissions)."
     ::= { brzaccVLAirInterface 4 }



  brzaccVLTransmitPowerTable OBJECT-TYPE
      SYNTAX SEQUENCE OF BrzaccVLTransmitPowerEntry
      MAX-ACCESS not-accessible
      STATUS current
      DESCRIPTION
      "Applicable to AU and SU.
       A table of transmit power parameters. "
      ::= { brzaccVLAirInterface 5}

  brzaccVLTransmitPowerEntry OBJECT-TYPE
      SYNTAX BrzaccVLTransmitPowerEntry
      MAX-ACCESS not-accessible
      STATUS current
      DESCRIPTION
      "Applicable to AU and SU.
       An entry in the Transmit Power Table."
      INDEX { brzaccVLTransmitPowerIdx }
      ::= { brzaccVLTransmitPowerTable 1 }

  BrzaccVLTransmitPowerEntry ::= SEQUENCE {  brzaccVLTransmitPowerIdx     INTEGER,
                        brzaccVLApplicableModulationLevel INTEGER,
                        brzaccVLMaximumTxPowerRange    DisplayString,
                        brzaccVLTxPower          DisplayString,
                        brzaccVLCurrentTxPower      DisplayString
                       }

  brzaccVLTransmitPowerIdx OBJECT-TYPE
      SYNTAX INTEGER
      MAX-ACCESS read-only
      STATUS current
      DESCRIPTION
      "Applicable to AU and SU.
       An index of an entry in the Transmit Power Table."
      ::= { brzaccVLTransmitPowerEntry 1 }


  brzaccVLApplicableModulationLevel    OBJECT-TYPE
      SYNTAX INTEGER {level1to5 (1), level6 (2), level7 (3), level8 (4)}
      MAX-ACCESS read-only
      STATUS current
      DESCRIPTION
      "Applicable to AU and SU.
       The applicable modulation level for an entry in the Transmit Power Table."
      ::= { brzaccVLTransmitPowerEntry 2 }

  brzaccVLMaximumTxPowerRange OBJECT-TYPE
      SYNTAX DisplayString
      MAX-ACCESS read-only
      STATUS current
      DESCRIPTION
      "Applicable to AU and SU.
       The allowed range for the brzaccVLTxPower parameter at the applicable modulation level .
       Range: -10 to the maximum allowed power level at the applicable modulation level , in dBm."
      ::= { brzaccVLTransmitPowerEntry 3 }


  brzaccVLTxPower OBJECT-TYPE
      SYNTAX DisplayString
      MAX-ACCESS read-write
      STATUS current
      DESCRIPTION
      "Applicable to AU and SU.
       In AU: The transmit power in dBm defined for the applicable rate.
       In SU: If ATPC is disabled, this is the transmit power in dBm defined for the applicable rate.
       If ATPC is enabled, it serves as the initial transmit power in dBm for the ATPC algorithm. "
      ::= { brzaccVLTransmitPowerEntry 4 }



  brzaccVLCurrentTxPower OBJECT-TYPE
      SYNTAX DisplayString
      MAX-ACCESS read-only
      STATUS current
      DESCRIPTION
      "Applicable to SU.
       The actual transmit power in dBm for the applicable rate.
       Range: -17 to the maximum value defined by brzaccVLMaximumTxPowerRange for the applicable rate."
      ::= { brzaccVLTransmitPowerEntry 5 }





  brzaccVLMaxNumOfAssociations OBJECT-TYPE
      SYNTAX INTEGER
      MAX-ACCESS read-write
      STATUS current
      DESCRIPTION
      "Applicable to AU only.
      Sets the upper limit for the number of Subscriber Units
      that can be associated with the AU.
      Range: 0 -512."
      ::= { brzaccVLAirInterface 10 }


brzaccVLBestAu  OBJECT IDENTIFIER ::= {brzaccVLAirInterface 11}

  brzaccVLBestAuSupport OBJECT-TYPE
      SYNTAX INTEGER { disable (1), enable (2), na (255) }
      MAX-ACCESS read-write
      STATUS current
      DESCRIPTION
      "Applicable to SU only.
       Disable/enable the Best AU selection mechanism."
      ::= { brzaccVLBestAu 1 }

  brzaccVLBestAuNoOfScanningAttempts OBJECT-TYPE
      SYNTAX INTEGER
      MAX-ACCESS read-write
      STATUS current
      DESCRIPTION
      "Applicable to SU only.
       The number of scanning attempts to collect information
       for the Best AU decision.
       Range: 1 to 255."
      ::= { brzaccVLBestAu 2 }

  brzaccVLPreferredAuMacAddress OBJECT-TYPE
      SYNTAX MacAddress
      MAX-ACCESS read-write
      STATUS current
      DESCRIPTION
      "Applicable to SU only.
       The MAC address of the preferred AU (overriding the
       Best AU selection process).
       000000000000 means no preferred AU."
      ::= { brzaccVLBestAu 3 }

  brzaccVLNeighborAuTable OBJECT-TYPE
      SYNTAX SEQUENCE OF BrzaccVLNeighborAuEntry
      MAX-ACCESS not-accessible
      STATUS current
      DESCRIPTION
      "Applicable to SU only.
       A table of data on neighboring AUs."
      ::= { brzaccVLBestAu 4}

  brzaccVLNeighborAuEntry OBJECT-TYPE
      SYNTAX BrzaccVLNeighborAuEntry
      MAX-ACCESS not-accessible
      STATUS current
      DESCRIPTION
      "Applicable to SU only.
       An entry in the Neighbor AU Table."
      INDEX { brzaccVLNeighborAuIdx }
      ::= { brzaccVLNeighborAuTable 1 }

  BrzaccVLNeighborAuEntry ::= SEQUENCE { brzaccVLNeighborAuIdx  INTEGER,
                brzaccVLNeighborAuMacAdd MacAddress,
                brzaccVLNeighborAuESSID DisplayString,
                brzaccVLNeighborAuSNR INTEGER,
                brzaccVLNeighborAuAssocLoadStatus INTEGER,
                brzaccVLNeighborAuMark INTEGER
                }

  brzaccVLNeighborAuIdx OBJECT-TYPE
      SYNTAX INTEGER
      MAX-ACCESS read-only
      STATUS current
      DESCRIPTION
      "Applicable to SU only.
       An index of an entry in the Neighbor AU Table."
      ::= { brzaccVLNeighborAuEntry 1 }

  brzaccVLNeighborAuMacAdd OBJECT-TYPE
      SYNTAX MacAddress
      MAX-ACCESS read-only
      STATUS current
      DESCRIPTION
      "Applicable to SU only.
       A MAC address of an AU in the Neighbor AU Table."
      ::= { brzaccVLNeighborAuEntry 2 }

  brzaccVLNeighborAuESSID OBJECT-TYPE
      SYNTAX DisplayString
      MAX-ACCESS read-only
      STATUS current
      DESCRIPTION
      "Applicable to SU only.
       The ESSID of an AU in the Neighbor AU Table.
       Accessible only with SNMP Write Community."
      ::= { brzaccVLNeighborAuEntry 3 }

  brzaccVLNeighborAuSNR OBJECT-TYPE
      SYNTAX INTEGER { na (255) }
      MAX-ACCESS read-only
      STATUS current
      DESCRIPTION
      "Applicable to SU only.
       The received signal quality (SNR) in dB of an AU
       in the Neighbor AU Table."
      ::= { brzaccVLNeighborAuEntry 4 }

  brzaccVLNeighborAuAssocLoadStatus OBJECT-TYPE
      SYNTAX INTEGER { full (1),notFull (2), na (255) }
      MAX-ACCESS read-only
      STATUS current
      DESCRIPTION
      "Applicable to SU only.
       Neighbor AU association load status in the Neighbor
       AU Table."
      ::= { brzaccVLNeighborAuEntry 5 }

  brzaccVLNeighborAuMark OBJECT-TYPE
      SYNTAX INTEGER
      MAX-ACCESS read-only
      STATUS current
      DESCRIPTION
      "Applicable to SU only.
       Neighbor AU mark in the Neighbor AU Table."
      ::= { brzaccVLNeighborAuEntry 6 }


brzaccVLFrequencyDefinition  OBJECT IDENTIFIER ::= {brzaccVLAirInterface 12}


  brzaccVLSubBandLowerFrequency OBJECT-TYPE
      SYNTAX INTEGER
      MAX-ACCESS read-write
      STATUS current
      DESCRIPTION
      "Applicable to SU only.
       The lowest frequency in the subset to be used for scanning.
       For 5.7GHz products the range is 5740 to 5830 MHz using 10MHz resolution"
      ::= { brzaccVLFrequencyDefinition 1 }

  brzaccVLSubBandUpperFrequency OBJECT-TYPE
      SYNTAX INTEGER
      MAX-ACCESS read-write
      STATUS current
      DESCRIPTION
      "Applicable to SU only.
       The highest frequency in the subset to be used for scanning.
       For 5.7GHz products the range is 5740 to 5830 MHz using 10MHz resolution "
      ::= { brzaccVLFrequencyDefinition 2 }

  brzaccVLScanningStep OBJECT-TYPE
      SYNTAX INTEGER { mhz_10(2) , mhz_20(3)}
      MAX-ACCESS read-write
      STATUS current
      DESCRIPTION
      "Applicable to SU only.
       The scanning step to be used for generating the frequency subset"
      ::= { brzaccVLFrequencyDefinition 3 }


  brzaccVLFrequencySubsetTable OBJECT-TYPE
      SYNTAX SEQUENCE OF BrzaccVLFrequencySubsetEntry
      MAX-ACCESS not-accessible
      STATUS current
      DESCRIPTION
      "Applicable to SU only.
       The Frequency Subset Table that includes all frequencies from
       the Sub-band Lower Frequency to the Sub-band Upper Frequency,
       using steps as defined by the Scanning Step."
        ::= { brzaccVLFrequencyDefinition 4 }

  brzaccVLFrequencySubsetEntry OBJECT-TYPE
      SYNTAX BrzaccVLFrequencySubsetEntry
      MAX-ACCESS not-accessible
      STATUS current
      DESCRIPTION
      "Applicable to SU only.
       An entry in the Frequency Subset Table. "
       INDEX { brzaccVLFrequencySubsetTableIdx }
      ::= { brzaccVLFrequencySubsetTable 1 }

  BrzaccVLFrequencySubsetEntry ::= SEQUENCE {
      brzaccVLFrequencySubsetTableIdx INTEGER,
      brzaccVLFrequencySubsetFrequency INTEGER,
      brzaccVLFrequencySubsetActive  INTEGER
      }

  brzaccVLFrequencySubsetTableIdx  OBJECT-TYPE
      SYNTAX INTEGER
      MAX-ACCESS read-only
      STATUS current
      DESCRIPTION
      "Applicable to SU only.
       An index of an entry in the Frequency subset Table."
      ::= { brzaccVLFrequencySubsetEntry 1 }


  brzaccVLFrequencySubsetFrequency  OBJECT-TYPE
      SYNTAX INTEGER
      MAX-ACCESS read-only
      STATUS current
      DESCRIPTION
      "Applicable to SU only.
       A frequency of an entry in the Frequency subset Table."
      ::= { brzaccVLFrequencySubsetEntry 2 }

  brzaccVLFrequencySubsetActive  OBJECT-TYPE
      SYNTAX INTEGER {active (1) , notActive (2)}
      MAX-ACCESS read-write
      STATUS current
      DESCRIPTION
      "Applicable to SU only.
       The status of an entry in the Frequency subset Table.
       The frequency of an active entry will be included in the
       final list of frequencies to be used for scanning."
      ::= { brzaccVLFrequencySubsetEntry 3 }


  brzaccVLSetSelectedFreqSubset OBJECT-TYPE
      SYNTAX INTEGER  {setSelectedFreqsSubset(1) ,cancel (2)}
      MAX-ACCESS read-write
      STATUS current
      DESCRIPTION
      "Applicable to SU only.
       Apply the selected subset.
       After the next reset the new subset will be used for scanning."
      ::= { brzaccVLFrequencyDefinition 5 }




  brzaccVLCurrentFrequencySubsetTable OBJECT-TYPE
      SYNTAX SEQUENCE OF BrzaccVLCurrentFrequencySubsetEntry
      MAX-ACCESS not-accessible
      STATUS current
      DESCRIPTION
      "Applicable to SU only.
       The Current Frequency Subset table that includes all
       frequencies that are currently used for scanning."
        ::= { brzaccVLFrequencyDefinition 6 }

  brzaccVLCurrentFrequencySubsetEntry OBJECT-TYPE
      SYNTAX BrzaccVLCurrentFrequencySubsetEntry
      MAX-ACCESS not-accessible
      STATUS current
      DESCRIPTION
      "Applicable to SU only.
       An entry in the Current Frequency Subset Table. "
       INDEX { brzaccVLCurrentFrequencySubsetTableIdx }
      ::= { brzaccVLCurrentFrequencySubsetTable 1 }

  BrzaccVLCurrentFrequencySubsetEntry ::= SEQUENCE {
      brzaccVLCurrentFrequencySubsetTableIdx INTEGER,
      brzaccVLCurrentFrequencySubsetFrequency INTEGER
      }

  brzaccVLCurrentFrequencySubsetTableIdx  OBJECT-TYPE
      SYNTAX INTEGER
      MAX-ACCESS read-only
      STATUS current
      DESCRIPTION
      "Applicable to SU only.
       An index of an entry in the Current Frequency subset Table."
      ::= { brzaccVLCurrentFrequencySubsetEntry 1 }


  brzaccVLCurrentFrequencySubsetFrequency  OBJECT-TYPE
      SYNTAX INTEGER
      MAX-ACCESS read-only
      STATUS current
      DESCRIPTION
      "Applicable to SU only.
       A frequency of an entry in the Current Frequency subset Table."
      ::= { brzaccVLCurrentFrequencySubsetEntry 2 }



  brzaccVLCurrentAUOperatingFrequency OBJECT-TYPE
      SYNTAX INTEGER
      MAX-ACCESS read-only
      STATUS current
      DESCRIPTION
      "Applicable to AU only.
       The operating frequency of the AU."
      ::= { brzaccVLFrequencyDefinition 7 }

  brzaccVLAUDefinedFrequency OBJECT-TYPE
      SYNTAX INTEGER
      MAX-ACCESS read-write
      STATUS current
      DESCRIPTION
      "Applicable to AU only.
       The frequency of the AU after the next reset."
      ::= { brzaccVLFrequencyDefinition 8 }

  brzaccVLCurrentSUOperatingFrequency OBJECT-TYPE
      SYNTAX DisplayString
      MAX-ACCESS read-only
      STATUS current
      DESCRIPTION
      "Applicable to SU only.
       The frequency used currently by the unit."
      ::= { brzaccVLFrequencyDefinition 9 }

brzaccVLATPC  OBJECT IDENTIFIER ::= {brzaccVLAirInterface 13}

  brzaccVLAtpcOption OBJECT-TYPE
      SYNTAX INTEGER { disable (1) , enable (2) , na (255) }
      MAX-ACCESS read-write
      STATUS current
      DESCRIPTION
      "Applicable AU and SU.
       Enabling/disabling the ATPC Algorithm."
      ::= { brzaccVLATPC 1 }

  brzaccVLDeltaFromMinSNRLevel OBJECT-TYPE
      SYNTAX INTEGER
      MAX-ACCESS read-write
      STATUS current
      DESCRIPTION
      "Applicable AU only.
       The Minimum SNR Level plus the value of this parameter define the maximum
       desired level of the average SNR at the AU. If the ATPC Option is enabled,
       than if the received SNR is above the maximum desired level, the AU will
       transmit Power-Down messages to the applicable SU.
       Range: 4 to 20."
      ::= { brzaccVLATPC 2 }

  brzaccVLMinimumSNRLevel OBJECT-TYPE
      SYNTAX INTEGER
      MAX-ACCESS read-write
      STATUS current
      DESCRIPTION
      "Applicable AU only.
       Defines the minimum desired level of the average SNR at the AU.
       Below this level, if *AtpcOption is enabled, the AU will transmit
       ATPC Power-Up messages to the applicable SU.
       The *MinimumSNRLevel cannot be higher than *MaximumSNRLevel.
       Range: 4 to 60."
      ::= { brzaccVLATPC 3 }


  brzaccVLMinimumIntervalBetweenATPCMessages OBJECT-TYPE
      SYNTAX INTEGER
      ACCESS read-write
      STATUS current
      DESCRIPTION
      "Applicable AU only.
       The minimum interval between two consecutive AU to SU messages.
       Range: 1 to 3600 (Sec)."
      ::= { brzaccVLATPC 4 }



  brzaccVLPowerLevelSteps OBJECT-TYPE
      SYNTAX INTEGER
      MAX-ACCESS read-write
      STATUS current
      DESCRIPTION
      "Applicable AU only.
       The step in dB that the SU will use when receiving an ATPC Power-Up/Power-Down message
       Range: 1 to 20."
      ::= { brzaccVLATPC 6 }



-- Service Params
-- ==============
--  brzaccVLServiceParameters    OBJECT IDENTIFIER ::= {breezeAccessVLMib 7}

--  brzaccVLMirCirOption OBJECT-TYPE
--  SYNTAX INTEGER {disable (1),
--           enable (2),
--           na (255)}
--    MAX-ACCESS read-write
--    STATUS current
--    DESCRIPTION
--    "Applicable to AU only.
--     The setting in the AU enables/disables the MIR/CIR support
--     feature for all SUs served by the AU."
--  ::= { brzaccVLServiceParameters 1 }
--
--  brzaccVLMirAUtoSU OBJECT-TYPE
--    SYNTAX INTEGER
--    MAX-ACCESS read-write
--    STATUS current
--    DESCRIPTION
--    "Applicable to SU only.
--     Sets the Maximum Information Rate (MIR) from AU to SU.
--     MIR must be above brzaccVLCirAUtoSU value.
--     Range: 32 - 2200 (Kbps)."
--  ::= { brzaccVLServiceParameters 2 }
--
--  brzaccVLMirSUtoAU OBJECT-TYPE
--    SYNTAX INTEGER
--    MAX-ACCESS read-write
--    STATUS current
--    DESCRIPTION
--    "Applicable to SU only.
--     Sets the Maximum Information Rate (MIR) from SU to AU.
--     MIR must be above brzaccVLCirSUtoAU value.
--     Range: 32 - 2200 (Kbps)."
--  ::= { brzaccVLServiceParameters 3 }
--
--
--  brzaccVLCirAUtoSU OBJECT-TYPE
--    SYNTAX INTEGER
--    MAX-ACCESS read-write
--    STATUS current
--    DESCRIPTION
--    "Applicable to SU only.
--     Sets the Committed Information Rate (CIR) from AU to SU.
--     CIR must be below brzaccVLMirAUtoSU value.
--     Range: 0 - 2200 (Kbps)."
--  ::= { brzaccVLServiceParameters 4 }
--
--
--  brzaccVLCirSUtoAU OBJECT-TYPE
--     SYNTAX INTEGER
--     MAX-ACCESS read-write
--     STATUS current
--     DESCRIPTION
--    "Applicable to SU only.
--     Sets the Committed Information Rate (CIR) from SU to AU.
--     CIR must be below brzaccVLMirSUtoAU value.
--     Range: 0 - 2200 (Kbps)."
--  ::= { brzaccVLServiceParameters 5 }


--  brzaccVLMaxDelay OBJECT-TYPE
--    SYNTAX INTEGER
--    MAX-ACCESS read-write
--    STATUS current
--    DESCRIPTION
--    "Applicable to SU only.
--     Sets the maximal time packets may be delayed by the
--     CIR\MIR mechanism. Above the configured maximal period
--     the packets are discarded.
--     Range: 300 - 10000 mili sec."
--  ::= { brzaccVLServiceParameters 6 }
--
--  brzaccVLMaxBurstDuration OBJECT-TYPE
--    SYNTAX INTEGER
--    MAX-ACCESS read-write
--    STATUS current
--    DESCRIPTION
--    "Applicable to AU and SU.
--     Sets the maximum time during which inactivity bonus time
--     can be accumulated for future burst transmissions.
--     Range: 0 - 2000 mili seconds."
--  ::= { brzaccVLServiceParameters 7 }

--  brzaccVLGracefulDegradationLimit OBJECT-TYPE
--    SYNTAX INTEGER
--    MAX-ACCESS read-write
--    STATUS current
--    DESCRIPTION
--    "Applicable to AU only.
--     Sets the maximum limit for activating the graceful
--     degradation algorithm.
--     Range: 0 - 70% rate of the CIR."
--  ::= { brzaccVLServiceParameters 8 }
--
--  brzaccVLMirOnlyOption OBJECT-TYPE
--    SYNTAX INTEGER {disable (1), enable (2), na (255)}
--    MAX-ACCESS read-write
--    STATUS current
--    DESCRIPTION
--    "Applicable only to AU when CIR/MIR option is enabled.
--     When brzaccMirOnly is enabled, it overrides the CIR/MIR
--     algorithm for determining actual information rate and
--     forces the algorithm to operate with MIR parameter
--     settings only. When enabled, the Graceful Degradation
--     algorithm is disabled."
--  ::= { brzaccVLServiceParameters 9 }

-- User Filtering Params
-- =====================
  brzaccVLUserFilterParams  OBJECT IDENTIFIER ::= {breezeAccessVLMib 8}

  brzaccVLUserFilterOption OBJECT-TYPE
      SYNTAX INTEGER { disable (1),
               ipOnly (2),
               userDefinedAddrOnly (3),
               pPPoEOnly (4),
               na (255) }
      MAX-ACCESS read-write
      STATUS current
      DESCRIPTION
      "Applicable to SU only.
       Defines user-filtering options.
       disable: No filtering.
       iPOnly: Only IP protocol frames pass.
       userDefinedAddrOnly: Only ip frames to/from user defined IP
                 addresses pass.
       pPPoE Only: Only PPPoE frames pass."
       ::= { brzaccVLUserFilterParams 1 }

  brzaccVLIpFilterTable OBJECT-TYPE
      SYNTAX SEQUENCE OF BrzaccVLIpFilterEntry
      MAX-ACCESS not-accessible
      STATUS current
      DESCRIPTION
        "Applicable to SU only.
        An IP Filter Table of up to 8 user defined addresses,
        or address groups, to be used if the selected User
        Filtering option is userDefinedAddrOnly."
        ::= { brzaccVLUserFilterParams 2 }

  brzaccVLIpFilterEntry OBJECT-TYPE
      SYNTAX BrzaccVLIpFilterEntry
      MAX-ACCESS not-accessible
      STATUS current
      DESCRIPTION
        "Applicable to SU only.
        An IP Filter Table entry."
        INDEX { brzaccVLIpFilterIdx }
        ::= { brzaccVLIpFilterTable 1 }

  BrzaccVLIpFilterEntry ::= SEQUENCE {
      brzaccVLIpID  IpAddress,
      brzaccVLMaskID IpAddress,
      brzaccVLIpFilterRange INTEGER,
      brzaccVLIpFilterIdx INTEGER
      }

  brzaccVLIpID  OBJECT-TYPE
      SYNTAX IpAddress
      MAX-ACCESS read-write
      STATUS current
      DESCRIPTION
      "Applicable to SU only.
       An IP address of an IP Filter Table entry."
      ::= { brzaccVLIpFilterEntry 1 }

  brzaccVLMaskID OBJECT-TYPE
      SYNTAX IpAddress
      MAX-ACCESS read-write
      STATUS current
      DESCRIPTION
      "Applicable to SU only.
       An IP Mask of an IP Filter Table entry. Either a mask
       or a range, but not both can be used to define an
       address group. If the range is other than 0, than the mask is
       ignored and only the range value is used to define the address group."
      ::= { brzaccVLIpFilterEntry 2 }

  brzaccVLIpFilterRange OBJECT-TYPE
      SYNTAX INTEGER
      MAX-ACCESS read-write
      STATUS current
      DESCRIPTION
      "Applicable to SU only.
       An addresses range for the IP Filter Table entry. The
       first address in the range is the IP address.
       O means that the range is not used.
       Either a mask or a range, but not both can be used to
       define an address group.
       If the range is other than 0, than the mask is ignored and
       only the range value is used to define the address group.
       Range: 0-255."
      ::= { brzaccVLIpFilterEntry 3 }

  brzaccVLIpFilterIdx  OBJECT-TYPE
      SYNTAX INTEGER
      MAX-ACCESS read-only
      STATUS current
      DESCRIPTION
      "Applicable to SU only. Read-only.
       A table index for the IP Filter Table entry."
     ::= { brzaccVLIpFilterEntry 4 }

  brzaccVLDeleteOneUserFilter OBJECT-TYPE
      SYNTAX INTEGER { deletefirstEntry (1), deletesecondEntry (2),
               deletethirdEntry (3), deletefourthEntry (4),
               deletefifthEntry (5), deletesixthEntry (6),
               deleteseventhEntry(7), deleteeighthEntry (8),
               cancelOperation  (9), na (255) }

      MAX-ACCESS read-write
      STATUS current
      DESCRIPTION
      "Applicable to SU only.
       Deletes a single selected entry from the IP Filter
       Table."
      ::= { brzaccVLUserFilterParams 3 }

  brzaccVLDeleteAllUserFilters OBJECT-TYPE
      SYNTAX INTEGER { deleteAll (1), cancelOperation (2),
               na (255) }
      MAX-ACCESS read-write
      STATUS current
      DESCRIPTION
      "Applicable to SU only.
       Deletes all entries from the IP Filter Table."
      ::= { brzaccVLUserFilterParams 4 }





-- Performance Params
-- ==================
brzaccVLPerformanceParams   OBJECT IDENTIFIER ::= {breezeAccessVLMib 10}

  brzaccVLRTSThreshold OBJECT-TYPE
      SYNTAX INTEGER
      MAX-ACCESS read-write
      STATUS current
      DESCRIPTION
      "Applicable to SU and AU.
       The minimum frame size that requires an RTS/CTS handshake.
       Range: 20 to 1600 bytes."
      ::= { brzaccVLPerformanceParams 1 }

  brzaccVLMinContentionWindow OBJECT-TYPE
      SYNTAX INTEGER
      MAX-ACCESS read-write
      STATUS current
      DESCRIPTION
      "Applicable to SU and AU.
       The initial value to be used by the contention window calculation algorithm.
       Value must be 0 or power of 2 minus 1 (7,15,31...)
       Range: 0 to 1023."
      ::= { brzaccVLPerformanceParams 3 }

  brzaccVLMaxContentionWindow OBJECT-TYPE
      SYNTAX INTEGER
      MAX-ACCESS read-write
      STATUS current
      DESCRIPTION
      "Applicable to SU and AU.
      The maximum value to be used by the contention window calculation algorithm.
       Value must be 0 or power of 2 minus 1 (7,15,31...)
       Range: 0 to 1023."
      ::= { brzaccVLPerformanceParams 4 }

  brzaccVLMaximumModulationLevel OBJECT-TYPE
      SYNTAX INTEGER { level1 (1),
               level2 (2),
               level3 (3),
               level4 (4),
               level5 (5),
               level6 (6),
               level7 (7),
               level8 (8)
              }
      MAX-ACCESS read-write
      STATUS current
      DESCRIPTION
      "Applicable to SU and AU.
       If the Adaptive Modulation algorithm is enabled, it sets the Maximum Modulation Level to be used.
       If The Modulation algorithm algorithm is disabled, it sets the Fixed Modulation Level to be used.
       The range is 1 to 8."
      ::= { brzaccVLPerformanceParams 5 }

  brzaccVLMulticastModulationLevel OBJECT-TYPE
      SYNTAX INTEGER { level1 (1),
               level2 (2),
               level3 (3),
               level4 (4),
               level5 (5),
               level6 (6),
               level7 (7),
               level8 (8)
              }

      MAX-ACCESS read-write
      STATUS current
      DESCRIPTION
      "Applicable to AU only.
       The modulation level for multicast and broadcast data frames.
       The range is 1 to 8."
      ::= { brzaccVLPerformanceParams 6 }



  brzaccVLAvgSNRMemoryFactor OBJECT-TYPE
      SYNTAX DisplayString
      MAX-ACCESS read-write
      STATUS current
      DESCRIPTION
      "Applicable AU only.
       The weight of history in average SNR calculation.
       The higher is the value, the higher is the weight of history.
       Range: -1 (Diregard History) to 32."
      ::= { brzaccVLPerformanceParams 7 }


  brzaccVLHardwareRetries OBJECT-TYPE
      SYNTAX INTEGER
      MAX-ACCESS read-write
      STATUS current
      DESCRIPTION
      "Applicable to SU and AU.
       The maximum number of trials to transmit an unacknowledged frame in each Hardware Retrial phase.
       Range : 1 to 15."
      ::= { brzaccVLPerformanceParams 8 }



brzaccVLAdaptiveModulationParams   OBJECT IDENTIFIER ::= {brzaccVLPerformanceParams 9}

  brzaccVLAdaptiveModulationAlgorithmOption OBJECT-TYPE
      SYNTAX INTEGER {  disable (1) , enable (2), na (255) }
      MAX-ACCESS read-write
      STATUS current
      DESCRIPTION
      "Applicable to SU and AU.
       Enables/disables the adaptive modulation level decision mechanism."
      ::= { brzaccVLAdaptiveModulationParams 1 }


  brzaccVLSoftwareRetrySupport OBJECT-TYPE
      SYNTAX INTEGER {  disable (1) , enable (2), na (255) }
      MAX-ACCESS read-write
      STATUS current
      DESCRIPTION
      "Applicable to SU and AU.
       Enabling/disabling the Software Retry mechanism when the Adaptive Modulation algorithm is enabled."
      ::= { brzaccVLAdaptiveModulationParams 2 }


  brzaccVLNumOfSoftwareRetries OBJECT-TYPE
      SYNTAX INTEGER
      MAX-ACCESS read-write
      STATUS current
      DESCRIPTION
      "Applicable to SU and AU.
       The maximum number of times to use the Software Retry mechanism when it is enabled.
       Range : 1 to 14"
      ::= { brzaccVLAdaptiveModulationParams 3 }



  brzaccVLMinimumIntervalBetweenAdaptiveModulationAlgorithmMessages OBJECT-TYPE
      SYNTAX INTEGER
      ACCESS read-write
      STATUS current
      DESCRIPTION
      "Applicable AU and SU.
       The minimum interval between two consecutive AU to SU messages.
       Range: 1 to 3600 (Sec)."
      ::= { brzaccVLAdaptiveModulationParams 4 }




-- Site Survey Params
-- ==================
brzaccVLSiteSurvey    OBJECT IDENTIFIER ::= {breezeAccessVLMib 11}

  brzaccVLAverageReceiveSNR OBJECT-TYPE
      SYNTAX INTEGER
      MAX-ACCESS read-only
      STATUS current
      DESCRIPTION
      "Applicable to SU only.
       The average Signal to Noise Ratio of received frames."
      ::= { brzaccVLSiteSurvey 1 }

-- Traffic Counters
-- ================
brzaccVLTrafficStatistics    OBJECT IDENTIFIER ::= {brzaccVLSiteSurvey 2}


  brzaccVLResetTrafficCounters OBJECT-TYPE
      SYNTAX INTEGER { reset (1),cancel(2) }
      MAX-ACCESS read-write
      STATUS current
      DESCRIPTION
      "Applicable to SU and AU.
       Resets the traffic counters."
      ::= { brzaccVLTrafficStatistics 1 }

brzaccVLEthCounters     OBJECT IDENTIFIER ::= {brzaccVLTrafficStatistics 2}
brzaccVLWirelessLinkCounters OBJECT IDENTIFIER ::= {brzaccVLTrafficStatistics 3}
brzaccVLWirelessLinkErrors  OBJECT IDENTIFIER ::= {brzaccVLTrafficStatistics 4}

brzaccVLPerModulationLevelCounters    OBJECT IDENTIFIER ::= {brzaccVLTrafficStatistics 5}


  brzaccVLResetPerModulationLevelCounters OBJECT-TYPE
      SYNTAX INTEGER { resetCounters(1) , cancel (2) }
      MAX-ACCESS read-write
      STATUS current
      DESCRIPTION
      "Applicable to AU and SU. Resets the per-Modulation Level counters ."
      ::= { brzaccVLPerModulationLevelCounters 1 }



  brzaccVLSUPerModulationLevelCountersTable OBJECT-TYPE
      SYNTAX SEQUENCE OF BrzaccVLSUPerModulationLevelCountersEntry
      MAX-ACCESS not-accessible
      STATUS current
      DESCRIPTION
      "Applicable to SU. Per Rate Counters table."
      ::= { brzaccVLPerModulationLevelCounters 2 }

  brzaccVLSUPerModulationLevelCountersEntry OBJECT-TYPE
      SYNTAX BrzaccVLSUPerModulationLevelCountersEntry
      MAX-ACCESS not-accessible
      STATUS current
      DESCRIPTION
      "Applicable to SU. An entry in the Per modulation Counters table."
      INDEX { brzaccVLSUPerModulationLevelCountersTableIdx }
      ::= { brzaccVLSUPerModulationLevelCountersTable 1 }

  BrzaccVLSUPerModulationLevelCountersEntry ::= SEQUENCE {
      brzaccVLSUPerModulationLevelCountersTableIdx    INTEGER,
      brzaccVLSUPerModulationLevelCountersApplicableModLevel INTEGER,
      brzaccVLSUPerModulationLevelCountersTxSuccess   INTEGER,
      brzaccVLSUPerModulationLevelCountersTxFailed  INTEGER
      }


  brzaccVLSUPerModulationLevelCountersTableIdx  OBJECT-TYPE
      SYNTAX INTEGER
      MAX-ACCESS read-only
      STATUS current
      DESCRIPTION
      "Applicable to SU.
       An index of an entry in the Per modulation level Counters table."
    ::= { brzaccVLSUPerModulationLevelCountersEntry 1 }

  brzaccVLSUPerModulationLevelCountersApplicableModLevel  OBJECT-TYPE
      SYNTAX INTEGER  {
                 modLevel-1 (1),
                 modLevel-2 (2),
                 modLevel-3 (3),
                 modLevel-4 (4),
                 modLevel-5 (5),
                 modLevel-6 (6),
                 modLevel-7 (7),
                 modLevel-8 (8)
                }
      MAX-ACCESS read-only
      STATUS current
      DESCRIPTION
      "Applicable to SU.
       The applicable modulation level of the entry in the Per modulation level Counters table."
    ::= { brzaccVLSUPerModulationLevelCountersEntry 2 }


  brzaccVLSUPerModulationLevelCountersTxSuccess   OBJECT-TYPE
      SYNTAX Counter32
      MAX-ACCESS read-only
      STATUS current
      DESCRIPTION
      "Applicable to SU.
       The total number of successfully transmitted unicasts at the applicable modulation level."
    ::= { brzaccVLSUPerModulationLevelCountersEntry 3 }


  brzaccVLSUPerModulationLevelCountersTxFailed  OBJECT-TYPE
      SYNTAX Counter32
      MAX-ACCESS read-only
      STATUS current
      DESCRIPTION
      "Applicable to SU.
       The total number of dropped frames at the applicable Modulation Level."
    ::= { brzaccVLSUPerModulationLevelCountersEntry 4 }



  brzaccVLTotalRxFramesViaEthernet OBJECT-TYPE
      SYNTAX Counter32
      MAX-ACCESS read-only
      STATUS current
      DESCRIPTION
      "Applicable to SU and AU.
       Total number of frames received via the Ethernet port."
      ::= { brzaccVLEthCounters 1 }

  brzaccVLTxWirelessToEthernet OBJECT-TYPE
      SYNTAX Counter32
      MAX-ACCESS read-only
      STATUS current
      DESCRIPTION
      "Applicable to SU and AU.
       Total number of frames transmitted to the Ethernet port."
      ::= { brzaccVLEthCounters 2 }

brzaccVLTxFramesToWireless  OBJECT IDENTIFIER ::= {brzaccVLWirelessLinkCounters 1}

  brzaccVLAUBeaconsToWireless OBJECT-TYPE
      SYNTAX Counter32
      MAX-ACCESS read-only
      STATUS current
      DESCRIPTION
      "Applicable to AU only.
       The number of beacons transmitted to the wireless media."
      ::= { brzaccVLTxFramesToWireless 1 }

--  brzaccVLOtherMngFramesToWireless OBJECT-TYPE
--       SYNTAX Counter32
--     MAX-ACCESS read-only
--     STATUS current
--     DESCRIPTION
--      "Applicable to AU and SU.
--       The number of management frames transmitted to the wireless media.
--       In AU, this count does not include Beacons."
--     ::= { brzaccVLTxFramesToWireless 2 }

  brzaccVLDataAndOtherMngFramesToWireless OBJECT-TYPE
      SYNTAX Counter32
      MAX-ACCESS read-only
      STATUS current
      DESCRIPTION
      "Applicable to AU only.
       The number of data and managment frames transmitted to the wireless media.
       The count includes one count for each data frame transmitted successfully (excluding retransmissions)."
      ::= { brzaccVLTxFramesToWireless 3 }

  brzaccVLTotalTxFramesToWireless OBJECT-TYPE
      SYNTAX Counter32
      MAX-ACCESS read-only
      STATUS current
      DESCRIPTION
      "Applicable to SU and AU.
       The number of frames transmitted to the wireless media.
       The count includes one count for each data frame
       that was transmitted successfully (excluding retransmissions),
       and also the number of transmitted control and management frames, including beacons."
      ::= { brzaccVLTxFramesToWireless 4 }

  brzaccVLTotalTransmittedUnicasts OBJECT-TYPE
      SYNTAX Counter32
      MAX-ACCESS read-only
      STATUS current
      DESCRIPTION
      "Applicable to AU only.
       The total number of unicast frames successfully transmitted
       to the wireless media, excluding retransmissions."
      ::= { brzaccVLTxFramesToWireless 5 }


  brzaccVLTotalRxFramesFromWireless OBJECT-TYPE
      SYNTAX Counter32
      MAX-ACCESS read-only
      STATUS current
      DESCRIPTION
      "Applicable to SU and AU.
       The total number of frames that were received
       from the wireless media.
       The count includes data and control and management
       frames, including beacons received from the AU.
       The count does not include frames that were discarded
       internally, bad frames and duplicate frames."
      ::= { brzaccVLWirelessLinkCounters 2 }

  brzaccVLTotalRetransmittedFrames OBJECT-TYPE
      SYNTAX Counter32
      MAX-ACCESS read-only
      STATUS current
      DESCRIPTION
      "Applicable to SU and AU.
       The total number of retransmissions of data frames
       (counts all unsuccessful transmissions/retransmissions)."
      ::= { brzaccVLWirelessLinkCounters 3 }

  brzaccVLFramesDropped OBJECT-TYPE
      SYNTAX Counter32
      MAX-ACCESS read-only
      STATUS current
      DESCRIPTION
      "Applicable to SU and AU.
       The number of dropped frames.
       The frames that were retransmitted to the extent
       of the maximum allowed number of retransmissions
       without being acknowledged.."
      ::= { brzaccVLWirelessLinkCounters 4 }


brzaccVLDataFramesSubmittedToBridge OBJECT IDENTIFIER ::= {brzaccVLWirelessLinkCounters 5}

  brzaccVLFramesSubmittedViaHighQueue OBJECT-TYPE
      SYNTAX Counter32
      MAX-ACCESS read-only
      STATUS current
      DESCRIPTION
      "Applicable to SU and AU.
       Frames submitted to the internal bridge via the High priority queue.
       for transmission to the wireless media."
      ::= { brzaccVLDataFramesSubmittedToBridge 1 }

  brzaccVLFramesSubmittedViaMidQueue OBJECT-TYPE
      SYNTAX Counter32
      MAX-ACCESS read-only
      STATUS current
      DESCRIPTION
      "Applicable to SU and AU.
       Frames submitted to the internal bridge via the Mid priority queue
       for transmission to the wireless media."
      ::= { brzaccVLDataFramesSubmittedToBridge 2 }

  brzaccVLFramesSubmittedViaLowQueue OBJECT-TYPE
      SYNTAX Counter32
      MAX-ACCESS read-only
      STATUS current
      DESCRIPTION
      "Applicable to SU and AU.
       Frames submitted to the internal bridge via the Low priority queue
       for transmission to the wireless media."
      ::= { brzaccVLDataFramesSubmittedToBridge 3 }

  brzaccVLTotalNoOfDataFramesSubmitted OBJECT-TYPE
      SYNTAX Counter32
      MAX-ACCESS read-only
      STATUS current
      DESCRIPTION
      "Applicable to SU and AU.
       The total number of data frames submitted to the internal bridge
       for transmission to the wireless media."
      ::= { brzaccVLDataFramesSubmittedToBridge 4 }


  brzaccVLTotalRecievedDataFrames OBJECT-TYPE
      SYNTAX Counter32
      MAX-ACCESS read-only
      STATUS current
      DESCRIPTION
      "Applicable to SU and AU.
       The total number of data frames received from the
       wireless media, including duplicate frames."
      ::= { brzaccVLWirelessLinkCounters 6 }

  brzaccVLRecievedBadFrames OBJECT-TYPE
      SYNTAX Counter32
      MAX-ACCESS read-only
      STATUS current
      DESCRIPTION
      "Applicable to SU and AU.
       The number of frames received from the wireless
       media with errors (CRC errors)."
      ::= { brzaccVLWirelessLinkCounters 7 }


  brzaccVLNoOfDuplicateFramesDiscarded OBJECT-TYPE
      SYNTAX Counter32
      MAX-ACCESS read-only
      STATUS current
      DESCRIPTION
      "Applicable to SU and AU.
       The number of frames discarded due to receiving multiple copies."
      ::= { brzaccVLWirelessLinkCounters 8 }



--  brzaccVLNoOfInternallyDiscardedMirCir OBJECT-TYPE
--       SYNTAX Counter32
--     MAX-ACCESS read-only
--     STATUS current
--     DESCRIPTION
--      "Applicable to SU and AU.
--       The number of data frames received from the
--       Ethernet port that were discarded by the MIR/CIR
--       mechanism to avoid exceeding the maximum allowed
--       information rate."
--     ::= { brzaccVLWirelessLinkCounters 9 }


-- brzaccVLInternallyGeneratedFramesSubmittedToBridge OBJECT-TYPE
--       SYNTAX Counter32
--     MAX-ACCESS read-only
--     STATUS current
--     DESCRIPTION
--      "Applicable to SU and AU. Read-only.
--       The number of internally generated frames(wireless management and control frames)
--       submitted to the bridge for transmission to the wireless media."
--     ::= { brzaccVLWirelessLinkCounters 10 }



brzaccVLTxErrors   OBJECT IDENTIFIER ::= {brzaccVLWirelessLinkErrors 1}

  brzaccVLDroppedFrameErrors OBJECT-TYPE
      SYNTAX Counter32
      MAX-ACCESS read-only
      STATUS current
      DESCRIPTION
      "Applicable to SU and AU.
       The number of Tx errors due to frames that were dropped because they were retransmitted
       to the maximum allowed number of retransmissions without being acknowledged The number
       of Tx frames dropped caused by to many retries."
      ::= { brzaccVLTxErrors 1 }

  brzaccVLFramesDelayedDueToSwRetry OBJECT-TYPE
      SYNTAX Counter32
      MAX-ACCESS read-only
      STATUS current
      DESCRIPTION
      "Applicable to SU and AU.
       The number of Tx errors due to frames that were delayed because the SW retry
       algorithm was activated on a previous frame designated for the same recipient."
      ::= { brzaccVLTxErrors 2 }


  brzaccVLUnderrunErrors OBJECT-TYPE
      SYNTAX Counter32
      MAX-ACCESS read-only
      STATUS current
      DESCRIPTION
      "Applicable to SU and AU.
       The number of Tx errors due to frames that were aborted because the rate
       of submitting frames for transmission exceeds the available transmission capability."
      ::= { brzaccVLTxErrors 3 }

  brzaccVLOthersTxError OBJECT-TYPE
      SYNTAX Counter32
      MAX-ACCESS read-only
      STATUS current
      DESCRIPTION
      "Applicable to SU and AU.
       The number of Tx errors due to errors other than those of the other Tx Errors counters ."
      ::= { brzaccVLTxErrors 4 }

  brzaccVLTotalTxErrors OBJECT-TYPE
      SYNTAX Counter32
      MAX-ACCESS read-only
      STATUS current
      DESCRIPTION
      "Applicable to SU and AU.
       The total number of Tx errors."
      ::= { brzaccVLTxErrors 5 }



brzaccVLRxErrors   OBJECT IDENTIFIER ::= {brzaccVLWirelessLinkErrors 2}

  brzaccVLPhyErrors OBJECT-TYPE
      SYNTAX Counter32
      MAX-ACCESS read-only
      STATUS current
      DESCRIPTION
      "Applicable to SU and AU.
       The number of frames that were not received properly due to a hardware problem."
      ::= { brzaccVLRxErrors 1 }

  brzaccVLCRCErrors OBJECT-TYPE
      SYNTAX Counter32
      MAX-ACCESS read-only
      STATUS current
      DESCRIPTION
      "Applicable to SU and AU.
       The number of frames received from the wireless media containing CRC errors."
      ::= { brzaccVLRxErrors 2 }


  brzaccVLOverrunErrors OBJECT-TYPE
      SYNTAX Counter32
      MAX-ACCESS read-only
      STATUS current
      DESCRIPTION
      "Applicable to SU and AU.
       The number of frames that were discarded because the receive rate exceeded
       the processing capability or the capacity of the Ethernet port."
      ::= { brzaccVLRxErrors 3 }

  brzaccVLOthersRxErrors OBJECT-TYPE
      SYNTAX Counter32
      MAX-ACCESS read-only
      STATUS current
      DESCRIPTION
      "Applicable to SU and AU. Read only.
       The number of Rx errors due to errors other than those of the other Rx Errors counters "
      ::= { brzaccVLRxErrors 4 }

  brzaccVLTotalRxErrors OBJECT-TYPE
      SYNTAX Counter32
      MAX-ACCESS read-only
      STATUS current
      DESCRIPTION
      "Applicable to SU and AU.
       The total number of Rx errors."
      ::= { brzaccVLRxErrors 5 }





-- Associations Database
--
brzaccVLMacAddressDatabase  OBJECT IDENTIFIER ::= {brzaccVLSiteSurvey 5}

brzaccVLAUMacAddressDatabase  OBJECT IDENTIFIER ::= {brzaccVLMacAddressDatabase 1}

brzaccVLAUAdbResetAllModulationLevelCounters OBJECT-TYPE
   SYNTAX INTEGER { reset (1), cancel (2) }
   MAX-ACCESS read-write
   STATUS current
   DESCRIPTION
   "Applicable to AU only.
    To reset all the counters for all SUs in the MAC Address Database."
   ::= { brzaccVLAUMacAddressDatabase 1 }

brzaccVLAUAdbTable OBJECT-TYPE
   SYNTAX SEQUENCE OF BrzaccVLAUAdbEntry
   MAX-ACCESS not-accessible
   STATUS current
   DESCRIPTION
   "Applicable to AU Only.
    AU MAC Address Database table."
   ::= { brzaccVLAUMacAddressDatabase 2 }

brzaccVLAUAdbEntry OBJECT-TYPE
   SYNTAX BrzaccVLAUAdbEntry
   MAX-ACCESS not-accessible
   STATUS current
   DESCRIPTION
   "Applicable to AU Only.
    An entry in the AU MAC Address Database table."
   INDEX { brzaccVLAdbIndex }
   ::= { brzaccVLAUAdbTable 1 }


BrzaccVLAUAdbEntry ::= SEQUENCE {
   brzaccVLAdbIndex       INTEGER,
   brzaccVLAdbMacAddress     MacAddress,
   brzaccVLAdbStatus       INTEGER,
   brzaccVLAdbSwVersion     DisplayString,
   brzaccVLAdbSNR        INTEGER,
   brzaccVLAdbMaxModulationLevel INTEGER,
   brzaccVLAdbTxFramesTotal   Counter32,
   brzaccVLAdbDroppedFramesTotal Counter32,
   brzaccVLAdbTxSuccessModLevel1   Counter32,
   brzaccVLAdbTxSuccessModLevel2   Counter32,
   brzaccVLAdbTxSuccessModLevel3   Counter32,
   brzaccVLAdbTxSuccessModLevel4   Counter32,
   brzaccVLAdbTxSuccessModLevel5   Counter32,
   brzaccVLAdbTxSuccessModLevel6   Counter32,
   brzaccVLAdbTxSuccessModLevel7   Counter32,
   brzaccVLAdbTxSuccessModLevel8   Counter32,
   brzaccVLAdbTxFailedModLevel1 Counter32,
   brzaccVLAdbTxFailedModLevel2 Counter32,
   brzaccVLAdbTxFailedModLevel3 Counter32,
   brzaccVLAdbTxFailedModLevel4 Counter32,
   brzaccVLAdbTxFailedModLevel5 Counter32,
   brzaccVLAdbTxFailedModLevel6 Counter32,
   brzaccVLAdbTxFailedModLevel7 Counter32,
   brzaccVLAdbTxFailedModLevel8 Counter32

   }

brzaccVLAdbIndex OBJECT-TYPE
   SYNTAX INTEGER
   MAX-ACCESS read-only
   STATUS current
   DESCRIPTION
   "Applicable to AU Only. Read-only.
    The index of an entry in the AU MAC Address Database table."
   ::= { brzaccVLAUAdbEntry 1 }

brzaccVLAdbMacAddress OBJECT-TYPE
   SYNTAX MacAddress
   MAX-ACCESS read-only
   STATUS current
   DESCRIPTION
   "Applicable to AU Only.
    The MAC Address of an SU entry in the MAC Address Database
    table."
   ::= { brzaccVLAUAdbEntry 2 }

brzaccVLAdbStatus  OBJECT-TYPE
   SYNTAX INTEGER { associated    (1),
            authenticated  (2),
            notAuthenticated (3) }
   MAX-ACCESS read-only
   STATUS current
   DESCRIPTION
   "Applicable to AU Only.
    The status of the relevant SU."
   ::= { brzaccVLAUAdbEntry 3 }

brzaccVLAdbSwVersion OBJECT-TYPE
   SYNTAX DisplayString
   MAX-ACCESS read-only
   STATUS current
   DESCRIPTION
   "Applicable to AU only.
    The SW version of the relevant SU."
   ::= { brzaccVLAUAdbEntry 4 }


brzaccVLAdbSNR OBJECT-TYPE
   SYNTAX INTEGER
   MAX-ACCESS read-only
   STATUS current
   DESCRIPTION
   "Applicable to AU only.
    The average Signal to Noise Ratio in dB of frames received by the AU from the relevant SU."
   ::= { brzaccVLAUAdbEntry 5 }

brzaccVLAdbMaxModulationLevel OBJECT-TYPE
   SYNTAX INTEGER { modLevel-1 (1),
            modLevel-2 (2),
            modLevel-3 (3),
            modLevel-4 (4),
            modLevel-5 (5),
            modLevel-6 (6),
            modLevel-7 (7),
            modLevel-8 (8)
           }
   MAX-ACCESS read-only
   STATUS current
   DESCRIPTION
   "Applicable to AU Only.
    The value configured in the relevant SU for the Maximum Modulation Level parameter."
   ::= { brzaccVLAUAdbEntry 6 }

brzaccVLAdbTxFramesTotal  OBJECT-TYPE
   SYNTAX Counter32
   MAX-ACCESS read-only
   STATUS current
   DESCRIPTION
   "Applicable to AU Only.
    Counts the total number of unicast frames (excluding retransmissions)
    that were successfully transmitted to the SU over the wireless link."
   ::= { brzaccVLAUAdbEntry 7 }

brzaccVLAdbDroppedFramesTotal OBJECT-TYPE
   SYNTAX Counter32
   MAX-ACCESS read-only
   STATUS current
   DESCRIPTION
   "Applicable to AU Only.
    Counts the total number of frames intended to the SU that
    were dropped because they were retransmitted to the extent
    of the maximum allowed number of retransmissions without
    being acknowledged."
   ::= { brzaccVLAUAdbEntry 8 }



brzaccVLAdbTxSuccessModLevel1  OBJECT-TYPE
   SYNTAX Counter32
   MAX-ACCESS read-only
   STATUS current
   DESCRIPTION
   "Applicable to AU Only. Read-only.
    Counts the total number of unicast frames (excluding retransmissions)
    that were successfully transmitted to the SU over the wireless link using modulation level 1."
   ::= { brzaccVLAUAdbEntry 9 }

brzaccVLAdbTxSuccessModLevel2  OBJECT-TYPE
   SYNTAX Counter32
   MAX-ACCESS read-only
   STATUS current
   DESCRIPTION
   "Applicable to AU Only. Read-only.
    Counts the total number of unicast frames (excluding retransmissions)
    that were successfully transmitted to the SU over the wireless link using modulation level 2."
   ::= { brzaccVLAUAdbEntry 10 }

brzaccVLAdbTxSuccessModLevel3  OBJECT-TYPE
   SYNTAX Counter32
   MAX-ACCESS read-only
   STATUS current
   DESCRIPTION
   "Applicable to AU Only. Read-only.
    Counts the total number of unicast frames (excluding retransmissions)
    that were successfully transmitted to the SU over the wireless link using modulation level 3."
   ::= { brzaccVLAUAdbEntry 11 }

brzaccVLAdbTxSuccessModLevel4  OBJECT-TYPE
   SYNTAX Counter32
   MAX-ACCESS read-only
   STATUS current
   DESCRIPTION
   "Applicable to AU Only. Read-only.
    Counts the total number of unicast frames (excluding retransmissions)
    that were successfully transmitted to the SU over the wireless link using modulation level 4."
   ::= { brzaccVLAUAdbEntry 12 }

brzaccVLAdbTxSuccessModLevel5  OBJECT-TYPE
   SYNTAX Counter32
   MAX-ACCESS read-only
   STATUS current
   DESCRIPTION
   "Applicable to AU Only. Read-only.
    Counts the total number of unicast frames (excluding retransmissions)
    that were successfully transmitted to the SU over the wireless link using modulation level 5."
   ::= { brzaccVLAUAdbEntry 13 }

brzaccVLAdbTxSuccessModLevel6  OBJECT-TYPE
   SYNTAX Counter32
   MAX-ACCESS read-only
   STATUS current
   DESCRIPTION
   "Applicable to AU Only. Read-only.
    Counts the total number of unicast frames (excluding retransmissions)
    that were successfully transmitted to the SU over the wireless link using modulation level 6."
   ::= { brzaccVLAUAdbEntry 14 }

brzaccVLAdbTxSuccessModLevel7  OBJECT-TYPE
   SYNTAX Counter32
   MAX-ACCESS read-only
   STATUS current
   DESCRIPTION
   "Applicable to AU Only. Read-only.
    Counts the total number of unicast frames (excluding retransmissions)
    that were successfully transmitted to the SU over the wireless link using modulation level 7."
   ::= { brzaccVLAUAdbEntry 15 }

brzaccVLAdbTxSuccessModLevel8  OBJECT-TYPE
   SYNTAX Counter32
   MAX-ACCESS read-only
   STATUS current
   DESCRIPTION
   "Applicable to AU Only. Read-only.
    Counts the total number of unicast frames (excluding retransmissions)
    that were successfully transmitted to the SU over the wireless link using modulation level 8"
   ::= { brzaccVLAUAdbEntry 16 }



brzaccVLAdbTxFailedModLevel1  OBJECT-TYPE
   SYNTAX Counter32
   MAX-ACCESS read-only
   STATUS current
   DESCRIPTION
   "Applicable to AU Only. Read-only.
    Counts the total number of failures to successfully
    transmit unicast frames intended to the SU using modulation level 1."
   ::= { brzaccVLAUAdbEntry 17 }

brzaccVLAdbTxFailedModLevel2  OBJECT-TYPE
   SYNTAX Counter32
   MAX-ACCESS read-only
   STATUS current
   DESCRIPTION
   "Applicable to AU Only. Read-only.
    Counts the total number of failures to successfully
    transmit unicast frames intended to the SU using modulation level 2."
   ::= { brzaccVLAUAdbEntry 18 }

brzaccVLAdbTxFailedModLevel3  OBJECT-TYPE
   SYNTAX Counter32
   MAX-ACCESS read-only
   STATUS current
   DESCRIPTION
   "Applicable to AU Only. Read-only.
    Counts the total number of failures to successfully
    transmit unicast frames intended to the SU using modulation level 3."
   ::= { brzaccVLAUAdbEntry 19 }

brzaccVLAdbTxFailedModLevel4  OBJECT-TYPE
   SYNTAX Counter32
   MAX-ACCESS read-only
   STATUS current
   DESCRIPTION
   "Applicable to AU Only. Read-only.
    Counts the total number of failures to successfully
    transmit unicast frames intended to the SU using modulation level 4."
   ::= { brzaccVLAUAdbEntry 20 }

brzaccVLAdbTxFailedModLevel5  OBJECT-TYPE
   SYNTAX Counter32
   MAX-ACCESS read-only
   STATUS current
   DESCRIPTION
   "Applicable to AU Only. Read-only.
    Counts the total number of failures to successfully
    transmit unicast frames intended to the SU using modulation level 5."
   ::= { brzaccVLAUAdbEntry 21 }

brzaccVLAdbTxFailedModLevel6  OBJECT-TYPE
   SYNTAX Counter32
   MAX-ACCESS read-only
   STATUS current
   DESCRIPTION
   "Applicable to AU Only. Read-only.
    Counts the total number of failures to successfully
    transmit unicast frames intended to the SU using modulation level 6."
   ::= { brzaccVLAUAdbEntry 22 }

brzaccVLAdbTxFailedModLevel7  OBJECT-TYPE
   SYNTAX Counter32
   MAX-ACCESS read-only
   STATUS current
   DESCRIPTION
   "Applicable to AU Only. Read-only.
    Counts the total number of failures to successfully
    transmit unicast frames intended to the SU using modulation level 7."
   ::= { brzaccVLAUAdbEntry 23 }

brzaccVLAdbTxFailedModLevel8  OBJECT-TYPE
   SYNTAX Counter32
   MAX-ACCESS read-only
   STATUS current
   DESCRIPTION
   "Applicable to AU Only. Read-only.
    Counts the total number of failures to successfully
    transmit unicast frames intended to the SU using modulation level 8."
   ::= { brzaccVLAUAdbEntry 24 }
















--brzaccVLSUMacAddressDatabase  OBJECT IDENTIFIER ::= {brzaccVLMacAddressDatabase 2}
--
--
--brzaccVLSUBridgingTable OBJECT-TYPE
--  SYNTAX SEQUENCE OF brzaccVLSUBridgingEntry
--  MAX-ACCESS not-accessible
--  STATUS current
--  DESCRIPTION
--   "Applicable to SU Only.
--    SU MAC Address Database table."
--  ::= { brzaccVLSUMacAddressDatabase 1 }
--
--brzaccVLSUBridgingEntry OBJECT-TYPE
--  SYNTAX brzaccVLSUBridgingEntry
--  MAX-ACCESS not-accessible
--  STATUS current
--   DESCRIPTION
--   "Applicable to SU Only.
--    An entry in the SU MAC Address Database table."
--  INDEX { brzaccVLSUBridgingIndex }
--  ::= { brzaccVLSUBridgingTable 1 }
--
--
--brzaccVLSUBridgingEntry ::= SEQUENCE {
--  brzaccVLSUBridgingIndex    INTEGER,
--  brzaccVLSUBridgingMacAddress MacAddress,
--  brzaccVLSUBridgingLearnedFrom INTEGER
--  }
--
--brzaccVLSUBridgingIndex OBJECT-TYPE
--  SYNTAX INTEGER
--  MAX-ACCESS read-only
--  STATUS current
--  DESCRIPTION
--  "Applicable to SU Only.
--   The index of an entry in the SU MAC Address Database table."
--  ::= { brzaccVLSUBridgingEntry 1 }
--
--brzaccVLSUBridgingMacAddress OBJECT-TYPE
--  SYNTAX MacAddress
--  MAX-ACCESS read-only
--  STATUS current
--  DESCRIPTION
--  "Applicable to SU Only."
--  ::= { brzaccVLSUBridgingEntry 2 }
--
--brzaccVLSUBridgingLearnedFrom OBJECT-TYPE
--  SYNTAX INTEGER { wireless (1),
--           ethernet (2) }
--  MAX-ACCESS read-only
--  STATUS current
--  DESCRIPTION
--  "Applicable to SU Only.
--   The port from which the relevant address was learned"
--  ::= { brzaccVLSUBridgingEntry 3 }



--brzaccVLAdbCurrentTxRate   OBJECT-TYPE
--  SYNTAX INTEGER
--  MAX-ACCESS read-only
--  STATUS current
--  DESCRIPTION
--  "Applicable to AU Only. Read-only.
--   The current transmit rate to the SU."
--  ::= { brzaccVLAUAdbEntry 4 }
--









-- ****************************************************************************************
-- TRAP defenitions:
-- ****************************************************************************************

brzaccVLTraps OBJECT IDENTIFIER ::= { breezeAccessVLMib 14 }

brzaccVLTrapSUMacAddr OBJECT-TYPE
  SYNTAX MacAddress
  MAX-ACCESS read-only
  STATUS current
  DESCRIPTION
  "Applicable to AU only.
   SU MAC Address."
  ::= { brzaccVLTraps 1 }

--brzaccVLTrapSNRQuality  OBJECT-TYPE
--  SYNTAX INTEGER
--  MAX-ACCESS read-only
--  STATUS current
--  DESCRIPTION
--  "Applicable to SU only.
--   SNR of received signal."
--  ::= { brzaccVLTraps 2 }

brzaccVLTrapText OBJECT-TYPE
  SYNTAX DisplayString
  MAX-ACCESS read-only
  STATUS current
  DESCRIPTION
  "Textual string for future use."
  ::= { brzaccVLTraps 3 }

brzaccVLTrapToggle  OBJECT-TYPE
  SYNTAX INTEGER{
    on (1),
    off (2)
    }
  MAX-ACCESS read-only
  STATUS current
  DESCRIPTION
  "Applicable to all products.
   An On/Off toggle status."
  ::= { brzaccVLTraps 4 }


brzaccVLTrapParameterChanged OBJECT-TYPE
  SYNTAX INTEGER{ ipFilter (2),
          vlan (4)}
  MAX-ACCESS read-only
  STATUS current
  DESCRIPTION
  "Applicable to AU and SU.
   A modification to one of the parameters related to
   IP Filtering or VLAN."
  ::= { brzaccVLTraps 5 }

brzaccVLTrapAccessRights OBJECT-TYPE
  SYNTAX INTEGER{ notLoggedIn  (1),
          readOnly   (2),
          installer   (3),
          administrator (4),
          factory    (5) }
  MAX-ACCESS read-only
  STATUS current
  DESCRIPTION
  "Applicable to all products.
   The access rights used for login."
  ::= { brzaccVLTraps 6 }

brzaccVLTrapLog  OBJECT-TYPE
  SYNTAX INTEGER{ telnetLogin (3),
          telnetLogout (4) }
  MAX-ACCESS read-only
  STATUS current
  DESCRIPTION
  "Applicable to all products.
   Login or logout to the Monitor program via Telnet."
  ::= { brzaccVLTraps 7 }

brzaccVLTrapTelnetUserIpAddress  OBJECT-TYPE
  SYNTAX IpAddress
  MAX-ACCESS read-only
  STATUS current
  DESCRIPTION
  "Applicable to AU and SU.
   The IP address of a Telnet user."
  ::= { brzaccVLTraps 8 }

brzaccVLTrapRTx  OBJECT-TYPE
  SYNTAX INTEGER
  MAX-ACCESS read-only
  STATUS current
  DESCRIPTION
  "Applicable to AU only.
   Retransmissions as a percentage of total transmissions."
  ::= { brzaccVLTraps 9 }


brzaccVLTrapFtpStatus  OBJECT-TYPE
  SYNTAX INTEGER{
    successful (1),
    failed (2)
    }
  MAX-ACCESS read-only
  STATUS current
  DESCRIPTION
  "Applicable to all products.
   The status of the last FTP loadloading procedure."
  ::= { brzaccVLTraps 10 }

--
-- Private Traps for BreezeAccessVL
--

brzaccVLSUassociatedAUTRAP TRAP-TYPE
  ENTERPRISE brzAccessVLProducts
  VARIABLES {
    brzaccVLTrapSUMacAddr   -- SU MAC address
    }
  --&amp;ACTIONS { log, minor, clrdups }
  --&amp;MESG "New SU associated (SU Mac Address: $1)"
  DESCRIPTION
   "An AU trap indicating a new association with an SU."
  ::= 2

brzaccVLAUdisassociatedTRAP TRAP-TYPE
  ENTERPRISE brzAccessVLProducts
  VARIABLES {
    brzaccVLTrapSUMacAddr   --Unit MAC address
    }
  DESCRIPTION
   "An AU trap indicating that an SU has been disassociated
    from the AU.
    The AU decides that an SU has been disassociated from it and remove it
    from the ADB after receiving from another AU a SNAP frame with the SU MAC address.
    The SNAP frame indicating a network topology change where the SU has associated with
    another AU will be received if both AUs are connected to the same Ethernet backbone"
  ::= 3

brzaccVLAUagingTRAP TRAP-TYPE
  ENTERPRISE brzAccessVLProducts
  VARIABLES {
    brzaccVLTrapSUMacAddr  -- Unit MAC address
    }
  --&amp;ACTIONS { log, minor, clrdups }
  --&amp;MESG "Unit was aged out (SU Mac Address: $1)"
  DESCRIPTION
   "An AU trap indicating that the unit association was aged out
    and removed from the Associates SUs database following its failure
    to acknowledge a specified number of consecutive frames."
  ::= 4

brzaccVLSUassociatedTRAP TRAP-TYPE
  ENTERPRISE brzAccessVLProducts
  VARIABLES {
--   brzaccVLLastAUMacAddress,     Old AU mac address
    brzaccVLAssociatedAU       -- New AU mac address
--   brzaccVLTrapLastSNRQuality,     Average SNR with old AU
  }
  --&amp;ACTIONS { log, minor, clrdups }
  --&amp;MESG "Associated with AU ( Mac Address $2)"
  DESCRIPTION
   "An SU trap indicating association with an AU.
    In addition to the MAC address information of the AU, the
    trap also includes information on the average SNR of frames
    received from the AU."
  ::= 6


brzaccVLAUwirelessQualityTRAP TRAP-TYPE
  ENTERPRISE brzAccessVLProducts
  VARIABLES {
    brzaccVLTrapToggle,
    brzaccVLTrapRTx
    }
  --&amp;ACTIONS { log, major, clrdups }
  --&amp;MESG "Quality of wireless link has been changed to $3"
  DESCRIPTION
    "An AU trap, indicating that the quality of the wireless
    link (retransmissions rate) has changed and dropped below (Off) or increased
    above (On) a threshold , defined by the *brzaccVLWirelessTrapThreshold.
    The threshold for AU is a percentage of retransmissions."
  ::= 20

brzaccVLPowerUpFromReset TRAP-TYPE
  ENTERPRISE brzAccessVLProducts
  VARIABLES {
    brzaccVLUnitMacAddress  -- Unit MAC address
    }
  --&amp;ACTIONS { log, minor, clrdups }
  --&amp;MESG "Power Up From Reset (Unit Mac Address: $'1)"
  DESCRIPTION
   "An AU trap indicating power up after Reset."
  ::= 101

brzaccVLTelnetStatusTRAP TRAP-TYPE
  ENTERPRISE brzAccessVLProducts
  VARIABLES {
    brzaccVLTrapLog,
    brzaccVLTrapAccessRights,
    brzaccVLTrapTelnetUserIpAddress
    }
  --&amp;ACTIONS { log, major, clrdups }
  --&amp;MESG "$'1 With Access Rights $'3 (Telnet User Ip Address is $2)"
  DESCRIPTION
   "A trap indicating that a log-in or log-out has been performed
    via Telnet. Includes the log-in access
    right and the IP address of the PC performing Telnet."
  ::= 102

brzaccVLParameterChangedTRAP TRAP-TYPE
  ENTERPRISE brzAccessVLProducts
  VARIABLES {
    brzaccVLTrapParameterChanged
    }
  --&amp;ACTIONS { log, major, clrdups }
  --&amp;MESG "A $'1 Parameter Changed"
  DESCRIPTION
   "An AU or SU trap indicating a change in a IP Filter or VLAN parameter."
  ::= 103


brzaccVLFtpLoadingStatusTRAP TRAP-TYPE
  ENTERPRISE brzAccessVLProducts
  VARIABLES {
    brzaccVLTrapFtpStatus,
    brzaccVLUnitMacAddress
    }
  --&amp;ACTIONS { log, major, clrdups }
  --&amp;MESG "File Transfer to unit is finished"
  DESCRIPTION
    "A trap indicating that last FTP loading process has been
    finished successfully or failed. "
  ::= 104

END
